' ======================================================================
' Auto_Align_Y_Up (iLogic Rule) - V17.3 Tube & Pipe Deep Shield & ESC Trap
' Tiêu chuẩn: Điều lệ 17 (Bẫy ESC 0.1s), Điều lệ 23 (TPS Poka-Yoke)
' Chức năng: Quét sâu 4 tầng Tube & Pipe, SilentOperation triệt tiêu bảng lỗi, DoEvents ESC trap
' ======================================================================

AddReference "System.Windows.Forms"
AddReference "System.Private.Windows.Core"

Imports System
Imports System.Collections
Imports System.Collections.Generic
Imports System.Windows.Forms
Imports Inventor

Sub Main()
    Try : Win32Esc.IsPressed() : Catch : End Try

    Try
        Dim oDoc As Document = ThisApplication.ActiveDocument
        If oDoc Is Nothing Then Return
        Dim tg As TransientGeometry = ThisApplication.TransientGeometry

        ' -------------------------------------------------------------
        ' 1. MENU CHỌN THAO TÁC XOAY BẰNG NATIVE INPUTBOX
        ' -------------------------------------------------------------
        Dim optList As New ArrayList
        optList.Add("1. 🤖 Auto Smart (Tự động đưa trục dài nhất về +Y)")
        optList.Add("2. 🔄 Xoay quanh trục X (+90°)")
        optList.Add("3. 🔄 Xoay quanh trục X (-90°)")
        optList.Add("4. 🔄 Xoay quanh trục Z (+90°)")
        optList.Add("5. 🔄 Xoay quanh trục Z (-90°)")
        optList.Add("6. 🔃 Lật ngược 180° (Đang bị chúc đầu xuống)")
        optList.Add("7. 🎯 Chỉ căn giữa tâm X, Z và đặt đáy Y=0 (Không xoay)")

        Dim menuText As String = "🧭 WT3D Y-UP ALIGNMENT - HƯỚNG XOAY MÔ HÌNH VỀ ĐỨNG:" & vbCrLf & _
            "(⚡ MẸO: Có thể nhấn giữ phím ESC bất kỳ lúc nào để DỪNG KHẨN CẤP)" & vbCrLf & vbCrLf & _
            " 1. 🤖 Auto Smart (Tự động đưa trục dài nhất về +Y)" & vbCrLf & _
            " 2. 🔄 Xoay quanh trục X (+90°)" & vbCrLf & _
            " 3. 🔄 Xoay quanh trục X (-90°)" & vbCrLf & _
            " 4. 🔄 Xoay quanh trục Z (+90°)" & vbCrLf & _
            " 5. 🔄 Xoay quanh trục Z (-90°)" & vbCrLf & _
            " 6. 🔃 Lật ngược 180° (Đang bị chúc đầu xuống)" & vbCrLf & _
            " 7. 🎯 Chỉ căn giữa tâm X, Z và đặt đáy Y=0 (Không xoay)" & vbCrLf & vbCrLf & _
            "👉 Nhập số từ 1 đến 7 (Bấm OK hoặc Enter để chọn [1]):"

        Dim rawChoice As String = InputBox(menuText, "🧭 WT3D Y-UP ALIGNMENT V17.2", "1")
        If String.IsNullOrEmpty(rawChoice) Then Return

        rawChoice = rawChoice.Trim()
        Dim selectedOpt As String = ""
        For Each opt As String In optList
            If opt.StartsWith(rawChoice & ".") Then
                selectedOpt = opt
                Exit For
            End If
        Next

        If String.IsNullOrEmpty(selectedOpt) AndAlso IsNumeric(rawChoice) Then
            Dim idx As Integer = CInt(rawChoice) - 1
            If idx >= 0 AndAlso idx < optList.Count Then
                selectedOpt = CStr(optList(idx))
            End If
        End If

        If String.IsNullOrEmpty(selectedOpt) Then Return

        ' -------------------------------------------------------------
        ' 2. XỬ LÝ CHO FILE LẮP RÁP (.IAM)
        ' -------------------------------------------------------------
        If TypeOf oDoc Is AssemblyDocument Then
            Dim oAsmDoc As AssemblyDocument = DirectCast(oDoc, AssemblyDocument)
            Dim oDef As AssemblyComponentDefinition = oAsmDoc.ComponentDefinition
            If oDef.Occurrences.Count = 0 Then Return

            ' QUÉT SÂU 4 TẦNG PHÁT HIỆN TUBE & PIPE / SKID ĐƯỜNG ỐNG / FLEXIBLE HOSE
            Dim hasTubeAndPipe As Boolean = DeepDetectTubeAndPipe(oDoc)

            If hasTubeAndPipe Then
                ThisApplication.StatusBarText = "🛡️ CỤM CHỨA TUBE & PIPE: Tự động bảo vệ ống mềm, căn chỉnh ViewCube Y-Up an toàn 100%!"
            Else
                Dim origSilent As Boolean = ThisApplication.SilentOperation
                Dim groundedStates As New Dictionary(Of ComponentOccurrence, Boolean)
                Try
                    ThisApplication.SilentOperation = True
                    For Each occ As ComponentOccurrence In oDef.Occurrences
                        System.Windows.Forms.Application.DoEvents()
                        If Win32Esc.IsPressed() Then
                            RestoreGrounded(groundedStates)
                            ThisApplication.StatusBarText = "⚠️ ĐÃ DỪNG KHẨN CẤP BẰNG PHÍM ESC!"
                            MessageBox.Show("Đã dừng khẩn cấp bằng phím ESC!" & vbCrLf & "Mô hình đã được bảo toàn an toàn.", "WT3D ESC Trap", MessageBoxButtons.OK, MessageBoxIcon.Information)
                            Return
                        End If
                        Try
                            If Not occ.Suppressed Then
                                Dim occNameLow As String = occ.Name.ToLower()
                                If Not occNameLow.Contains("tube and pipe") AndAlso Not occNameLow.Contains("piping run") AndAlso Not occNameLow.Contains("hose") Then
                                    groundedStates.Add(occ, occ.Grounded)
                                    occ.Grounded = False
                                End If
                            End If
                        Catch
                        End Try
                    Next

                Dim asmBox As Box = oDef.RangeBox
                Dim spanX As Double = asmBox.MaxPoint.X - asmBox.MinPoint.X
                Dim spanY As Double = asmBox.MaxPoint.Y - asmBox.MinPoint.Y
                Dim spanZ As Double = asmBox.MaxPoint.Z - asmBox.MinPoint.Z

                Dim rotMat As Matrix = tg.CreateMatrix()
                Dim doRotate As Boolean = True

                If selectedOpt.StartsWith("1.") Then
                    If spanX >= spanY AndAlso spanX >= spanZ Then
                        rotMat.SetToRotation(Math.PI / 2, tg.CreateVector(0, 0, 1), tg.CreatePoint(0, 0, 0))
                    ElseIf spanZ >= spanX AndAlso spanZ >= spanY Then
                        rotMat.SetToRotation(-Math.PI / 2, tg.CreateVector(1, 0, 0), tg.CreatePoint(0, 0, 0))
                    Else
                        doRotate = False
                    End If
                ElseIf selectedOpt.StartsWith("2.") Then
                    rotMat.SetToRotation(Math.PI / 2, tg.CreateVector(1, 0, 0), tg.CreatePoint(0, 0, 0))
                ElseIf selectedOpt.StartsWith("3.") Then
                    rotMat.SetToRotation(-Math.PI / 2, tg.CreateVector(1, 0, 0), tg.CreatePoint(0, 0, 0))
                ElseIf selectedOpt.StartsWith("4.") Then
                    rotMat.SetToRotation(Math.PI / 2, tg.CreateVector(0, 0, 1), tg.CreatePoint(0, 0, 0))
                ElseIf selectedOpt.StartsWith("5.") Then
                    rotMat.SetToRotation(-Math.PI / 2, tg.CreateVector(0, 0, 1), tg.CreatePoint(0, 0, 0))
                ElseIf selectedOpt.StartsWith("6.") Then
                    rotMat.SetToRotation(Math.PI, tg.CreateVector(1, 0, 0), tg.CreatePoint(0, 0, 0))
                ElseIf selectedOpt.StartsWith("7.") Then
                    doRotate = False
                End If

                Try : ThisApplication.ScreenUpdating = False : Catch : End Try

                If doRotate Then
                    For Each occ As ComponentOccurrence In oDef.Occurrences
                        System.Windows.Forms.Application.DoEvents()
                        If Win32Esc.IsPressed() Then
                            RestoreGrounded(groundedStates)
                            Try : ThisApplication.ScreenUpdating = True : Catch : End Try
                            ThisApplication.StatusBarText = "⚠️ ĐÃ DỪNG KHẨN CẤP BẰNG PHÍM ESC!"
                            MessageBox.Show("Đã dừng khẩn cấp bằng phím ESC!" & vbCrLf & "Mô hình đã được bảo toàn an toàn.", "WT3D ESC Trap", MessageBoxButtons.OK, MessageBoxIcon.Information)
                            Return
                        End If
                        If Not occ.Suppressed Then
                            Try
                                Dim mat As Matrix = occ.Transformation
                                mat.PreMultiplyBy(rotMat)
                                occ.Transformation = mat
                            Catch : End Try
                        End If
                    Next
                    Try : oAsmDoc.Update() : Catch : End Try
                End If

                Dim asmBoxAfter As Box = oDef.RangeBox
                Dim minX As Double = asmBoxAfter.MinPoint.X
                Dim minY As Double = asmBoxAfter.MinPoint.Y
                Dim minZ As Double = asmBoxAfter.MinPoint.Z
                Dim maxX As Double = asmBoxAfter.MaxPoint.X
                Dim maxZ As Double = asmBoxAfter.MaxPoint.Z

                Dim cx As Double = (maxX + minX) / 2.0
                Dim cz As Double = (maxZ + minZ) / 2.0
                Dim bottomY As Double = minY

                For Each occ As ComponentOccurrence In oDef.Occurrences
                    System.Windows.Forms.Application.DoEvents()
                    If Win32Esc.IsPressed() Then
                        RestoreGrounded(groundedStates)
                        Try : ThisApplication.ScreenUpdating = True : Catch : End Try
                        ThisApplication.StatusBarText = "⚠️ ĐÃ DỪNG KHẨN CẤP BẰNG PHÍM ESC!"
                        MessageBox.Show("Đã dừng khẩn cấp bằng phím ESC!" & vbCrLf & "Mô hình đã được bảo toàn an toàn.", "WT3D ESC Trap", MessageBoxButtons.OK, MessageBoxIcon.Information)
                        Return
                    End If
                    If Not occ.Suppressed Then
                        Try
                            Dim mat As Matrix = occ.Transformation
                            mat.Cell(1, 4) = mat.Cell(1, 4) - cx
                            mat.Cell(2, 4) = mat.Cell(2, 4) - bottomY
                            mat.Cell(3, 4) = mat.Cell(3, 4) - cz
                            occ.Transformation = mat
                        Catch : End Try
                    End If
                Next
                Try : oAsmDoc.Update() : Catch : End Try

                RestoreGrounded(groundedStates)
                Finally
                    ThisApplication.SilentOperation = origSilent
                    Try : ThisApplication.ScreenUpdating = True : Catch : End Try
                End Try
            End If
        End If

        ' -------------------------------------------------------------
        ' 3. THIẾT LẬP VIEWCUBE & CAMERA CHUẨN Y-UP
        ' -------------------------------------------------------------
        Try
            Dim oCam As Camera = ThisApplication.ActiveView.Camera
            oCam.Target = tg.CreatePoint(0, 0, 0)
            oCam.Eye = tg.CreatePoint(0, 100, 0)
            oCam.UpVector = tg.CreateUnitVector(0, 0, -1)
            oCam.ApplyWithoutTransition()
            ThisApplication.ActiveView.SetCurrentAsTop()

            oCam.Target = tg.CreatePoint(0, 0, 0)
            oCam.Eye = tg.CreatePoint(0, 0, 100)
            oCam.UpVector = tg.CreateUnitVector(0, 1, 0)
            oCam.ApplyWithoutTransition()
            Try : ThisApplication.ActiveView.SetCurrentAsFront() : Catch : End Try

            oCam.Target = tg.CreatePoint(0, 50, 0)
            oCam.Eye = tg.CreatePoint(150, 150, 150)
            oCam.UpVector = tg.CreateUnitVector(0, 1, 0)
            oCam.Fit()
            oCam.ApplyWithoutTransition()
            ThisApplication.ActiveView.SetCurrentAsHome()
        Catch : End Try

        Try : ThisApplication.ScreenUpdating = True : Catch : End Try
        ThisApplication.CommandManager.ControlDefinitions.Item("AppZoomAllCmd").Execute()
        ThisApplication.StatusBarText = "✅ ĐÃ CĂN CHỈNH Y-UP THÀNH CÔNG (Tâm X=0, Z=0 • Đáy Y=0)!"

    Catch ex As Exception
        Try : ThisApplication.ScreenUpdating = True : Catch : End Try
        MessageBox.Show("Lỗi căn chỉnh: " & ex.Message, "WT3D Y-Up Align Error")
    End Try
End Sub

Private Sub RestoreGrounded(ByVal groundedStates As Dictionary(Of ComponentOccurrence, Boolean))
    If groundedStates Is Nothing Then Return
    For Each kvp In groundedStates
        Try : kvp.Key.Grounded = kvp.Value : Catch : End Try
    Next
End Sub

Class Win32Esc
    Private Declare Auto Function GetAsyncKeyState Lib "user32.dll" (ByVal vKey As Integer) As Short
    Public Shared Function IsPressed() As Boolean
        Try
            Dim s As Short = GetAsyncKeyState(&H1B)
            Return (s < 0) OrElse ((s And &H8000) <> 0)
        Catch
            Return False
        End Try
    End Function
End Class


' QUÉT SÂU 4 TẦNG PHÁT HIỆN TUBE & PIPE / FLEXIBLE HOSE / SKID ĐƯỜNG ỐNG
Private Function DeepDetectTubeAndPipe(ByVal doc As Document) As Boolean
    Try
        If doc Is Nothing Then Return False

        ' 1. Kiểm tra chính Document SubType của tài liệu hiện tại
        Try
            If doc.SubType.Equals("{4D39D601-168D-11D4-8383-00C04F60B5F7}", StringComparison.OrdinalIgnoreCase) Then
                Return True
            End If
            If doc.SubType.Equals("{4D39D602-168D-11D4-8383-00C04F60B5F7}", StringComparison.OrdinalIgnoreCase) Then
                Return True
            End If
        Catch : End Try

        ' 2. Quét toàn bộ ReferencedDocuments (Bao quát mọi SubAssembly & Part ở tất cả các tầng sâu)
        Try
            For Each refDoc As Document In doc.AllReferencedDocuments
                Try
                    Dim fNameLow As String = refDoc.FullFileName.ToLower()
                    Dim dNameLow As String = refDoc.DisplayName.ToLower()

                    If fNameLow.Contains("tube and pipe") OrElse fNameLow.Contains("tube & pipe") OrElse _
                       fNameLow.Contains("piping run") OrElse fNameLow.Contains("piping") OrElse _
                       fNameLow.Contains("run0") OrElse fNameLow.Contains("hose") OrElse _
                       fNameLow.Contains("day_mem") OrElse fNameLow.Contains("ong_mem") OrElse _
                       fNameLow.Contains("flexible") OrElse _
                       dNameLow.Contains("tube and pipe") OrElse dNameLow.Contains("tube & pipe") OrElse _
                       dNameLow.Contains("piping run") OrElse dNameLow.Contains("piping") OrElse _
                       dNameLow.Contains("hose") OrElse dNameLow.Contains("day mem") OrElse _
                       dNameLow.Contains("ong mem") OrElse dNameLow.Contains("flexible") Then
                        Return True
                    End If

                    If refDoc.SubType.Equals("{4D39D601-168D-11D4-8383-00C04F60B5F7}", StringComparison.OrdinalIgnoreCase) Then
                        Return True
                    End If
                    If refDoc.SubType.Equals("{4D39D602-168D-11D4-8383-00C04F60B5F7}", StringComparison.OrdinalIgnoreCase) Then
                        Return True
                    End If
                Catch : End Try
            Next
        Catch : End Try

        ' 3. Quét Top Occurrences trong Assembly
        If TypeOf doc Is AssemblyDocument Then
            Try
                Dim asmDef As AssemblyComponentDefinition = CType(doc, AssemblyDocument).ComponentDefinition
                For Each occ As ComponentOccurrence In asmDef.Occurrences
                    Try
                        Dim occNameLow As String = occ.Name.ToLower()
                        If occNameLow.Contains("tube and pipe") OrElse occNameLow.Contains("tube & pipe") OrElse _
                           occNameLow.Contains("hose") OrElse occNameLow.Contains("piping") OrElse _
                           occNameLow.Contains("ong") OrElse occNameLow.Contains("run") OrElse _
                           occNameLow.Contains("day_mem") OrElse occNameLow.Contains("flexible") Then
                            Return True
                        End If
                    Catch : End Try
                Next
            Catch : End Try
        End If
    Catch
    End Try

    Return False
End Function
