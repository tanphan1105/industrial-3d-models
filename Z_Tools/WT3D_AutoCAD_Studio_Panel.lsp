; WT3D PRO LISP - AUTOCAD 2025 MASTER CONTROL PANEL (100% Pure ASCII)
; Tich hop 4 file: CUTDIM, NETCAT, NetNuoc, NN

(defun c:WT (/ dcl_file f dcl_id act)
  (vl-load-com)
  (setq dcl_file (strcat (getvar "TEMPPREFIX") "wt3d_p.dcl"))
  (setq f (open dcl_file "w"))
  (write-line "wt3d_p : dialog { label = \"WT3D STUDIO - AUTOCAD 2025 MASTER PANEL\"; : column { : button { key = \"btn1\"; label = \"1. Lam Nhe He Thong (0ms Delay, Muot)\"; width = 50; height = 2; is_default = true; } : button { key = \"btn2\"; label = \"2. Don Rac & Sua Loi Ban Ve (Purge All)\"; width = 50; } : button { key = \"btn3\"; label = \"3. Phuc Hoi Cai Dat Mac Dinh Goc (Reset)\"; width = 50; } spacer; : button { key = \"btn4\"; label = \"4. Chuyen VNI -> Unicode (Arial / Tahoma)\"; width = 50; height = 2; } : button { key = \"btn5\"; label = \"5. Quet Chon Vung & Doi Font Khong Chan\"; width = 50; } spacer; : button { key = \"btn6\"; label = \"6. Cat Chan Duong Dim (Lenh CD / BD)\"; width = 50; } : button { key = \"btn7\"; label = \"7. Ve Net Cat Ky Thuat (Lenh NC)\"; width = 50; } : button { key = \"btn8\"; label = \"8. Noi Net Polyline Nhanh (Lenh NN)\"; width = 50; } : button { key = \"btn9\"; label = \"9. Cai Dat Layer Duong Ong Nuoc\"; width = 50; } spacer; : button { key = \"cancel\"; label = \"Dong\"; is_cancel = true; alignment = centered; width = 14; } }}" f)
  (close f)
  (setq dcl_id (load_dialog dcl_file))
  (if (> dcl_id 0)
    (if (new_dialog "wt3d_p" dcl_id)
      (progn
        (action_tile "btn1" "(done_dialog 1)")
        (action_tile "btn2" "(done_dialog 2)")
        (action_tile "btn3" "(done_dialog 3)")
        (action_tile "btn4" "(done_dialog 4)")
        (action_tile "btn5" "(done_dialog 5)")
        (action_tile "btn6" "(done_dialog 6)")
        (action_tile "btn7" "(done_dialog 7)")
        (action_tile "btn8" "(done_dialog 8)")
        (action_tile "btn9" "(done_dialog 9)")
        (action_tile "cancel" "(done_dialog 0)")
        (setq act (start_dialog))
        (unload_dialog dcl_id)
        (vl-file-delete dcl_file)
        (cond
          ((= act 1) (c:WT3D_FAST))
          ((= act 2)
            (command "-purge" "all" "*" "n")
            (command "-purge" "regapps" "*" "n")
            (command "_.audit" "y")
            (princ "\n[WT3D] Don rac & sua loi ban ve xong!\n")
          )
          ((= act 3) (c:WT3D_RESET))
          ((= act 4) (c:V2U))
          ((= act 5) (c:SF))
          ((= act 6) (if (findfile "D:/PhanMem/lenhcad/CAD/CUTDIM.LSP") (load "D:/PhanMem/lenhcad/CAD/CUTDIM.LSP")) (c:CD))
          ((= act 7) (if (findfile "D:/PhanMem/lenhcad/CAD/NETCAT.LSP") (load "D:/PhanMem/lenhcad/CAD/NETCAT.LSP")) (c:NC))
          ((= act 8) (if (findfile "D:/PhanMem/lenhcad/CAD/NN.LSP") (load "D:/PhanMem/lenhcad/CAD/NN.LSP")) (c:NN))
          ((= act 9) (if (findfile "D:/PhanMem/lenhcad/CAD/NetNuoc.lsp") (load "D:/PhanMem/lenhcad/CAD/NetNuoc.lsp")) (c:CAIDAT_NETNUOC))
        )
      )
      (princ "\n[WT3D] new_dialog that bai - Ten dialog sai!\n")
    )
    (princ "\n[WT3D] load_dialog that bai - DCL loi cu phap!\n")
  )
  (princ)
)

(defun c:WT3D () (c:WT))
(defun c:W3D () (c:WT))

; --- TOI UU HIEU NANG 0MS ---
(defun c:WT3D_FAST ()
  (vl-load-com)
  (setvar "VTDURATION" 0)
  (setvar "HPQUICKPREVIEW" 0)
  (setvar "SELECTIONCYCLING" 0)
  (setvar "ROLLOVERTOOLTIPS" 0)
  (setvar "SELECTIONEFFECT" 0)
  (setvar "PRESELECTIONEFFECT" 0)
  (setvar "LINESMOOTHING" 0)
  (setvar "INPUTSEARCHDELAY" 200)
  (setvar "DWGCHECK" 0)
  (setvar "INDEXCTL" 3)
  (setvar "XLOADCTL" 2)
  (setvar "PALETTEOPAQUE" 1)
  (setvar "OSMODE" 4287)
  (setvar "AUTOSNAP" 63)
  (setvar "CURSORSIZE" 100)
  (setvar "APERTURE" 10)
  (setvar "GRIPSIZE" 5)
  (setvar "PICKFIRST" 1)
  (setvar "PICKADD" 2)
  (setvar "DRAWORDERCTL" 3)
  (setvar "DIMASSOC" 2)
  (princ "\n[WT3D] DA TOI UU HOA 0ms - HE THONG MUOT!\n")
  (princ)
)

; --- PHUC HOI MAC DINH GOC ---
(defun c:WT3D_RESET ()
  (vl-load-com)
  (setvar "VTDURATION" 750)
  (setvar "HPQUICKPREVIEW" 1)
  (setvar "SELECTIONCYCLING" 0)
  (setvar "ROLLOVERTOOLTIPS" 1)
  (setvar "SELECTIONEFFECT" 1)
  (setvar "PRESELECTIONEFFECT" 1)
  (setvar "LINESMOOTHING" 1)
  (setvar "INPUTSEARCHDELAY" 500)
  (setvar "DWGCHECK" 1)
  (setvar "INDEXCTL" 0)
  (setvar "XLOADCTL" 1)
  (setvar "PALETTEOPAQUE" 0)
  (setvar "CURSORSIZE" 5)
  (princ "\n[WT3D] DA KHOI PHUC CAI DAT MAC DINH GOC!\n")
  (princ)
)

; --- HAM THAY THE CHUOI ---
(defun wt3d-rep (pat rep str / pos len)
  (setq len (strlen pat))
  (while (setq pos (vl-string-search pat str))
    (setq str (strcat (substr str 1 pos) rep (substr str (+ pos len 1))))
  )
  str
)

; --- KHU SACH MA DINH DANG FONT AN TRONG MTEXT (STRIP FONT OVERRIDES) ---
(defun wt3d-strip-font (str / pos semi)
  (while (or (setq pos (vl-string-search "\\f" (strcase str t)))
             (setq pos (vl-string-search "\\F" str)))
    (setq semi (vl-string-search ";" str pos))
    (if semi
      (setq str (strcat (substr str 1 pos) (substr str (+ semi 2))))
      (setq pos nil)
    )
  )
  str
)

; --- CHUYEN VNI SANG UNICODE ---
(defun wt3d-vni-convert (s)
  (setq s (wt3d-rep (strcat "A" (chr 217)) "\\U+00C1" s))
  (setq s (wt3d-rep (strcat "A" (chr 216)) "\\U+00C0" s))
  (setq s (wt3d-rep (strcat "A" (chr 219)) "\\U+1EA2" s))
  (setq s (wt3d-rep (strcat "A" (chr 213)) "\\U+00C3" s))
  (setq s (wt3d-rep (strcat "A" (chr 207)) "\\U+1EA0" s))
  (setq s (wt3d-rep (strcat "a" (chr 249)) "\\U+00E1" s))
  (setq s (wt3d-rep (strcat "a" (chr 248)) "\\U+00E0" s))
  (setq s (wt3d-rep (strcat "a" (chr 251)) "\\U+1EA3" s))
  (setq s (wt3d-rep (strcat "a" (chr 245)) "\\U+00E3" s))
  (setq s (wt3d-rep (strcat "a" (chr 239)) "\\U+1EA1" s))
  (setq s (wt3d-rep (strcat "E" (chr 217)) "\\U+00C9" s))
  (setq s (wt3d-rep (strcat "E" (chr 216)) "\\U+00C8" s))
  (setq s (wt3d-rep (strcat "E" (chr 219)) "\\U+1EBA" s))
  (setq s (wt3d-rep (strcat "E" (chr 213)) "\\U+1EBC" s))
  (setq s (wt3d-rep (strcat "E" (chr 207)) "\\U+1EB8" s))
  (setq s (wt3d-rep (strcat "e" (chr 249)) "\\U+00E9" s))
  (setq s (wt3d-rep (strcat "e" (chr 248)) "\\U+00E8" s))
  (setq s (wt3d-rep (strcat "e" (chr 251)) "\\U+1EBB" s))
  (setq s (wt3d-rep (strcat "e" (chr 245)) "\\U+1EBD" s))
  (setq s (wt3d-rep (strcat "e" (chr 239)) "\\U+1EB9" s))
  (setq s (wt3d-rep (strcat "O" (chr 217)) "\\U+00D3" s))
  (setq s (wt3d-rep (strcat "O" (chr 216)) "\\U+00D2" s))
  (setq s (wt3d-rep (strcat "O" (chr 219)) "\\U+1ECE" s))
  (setq s (wt3d-rep (strcat "O" (chr 213)) "\\U+00D5" s))
  (setq s (wt3d-rep (strcat "O" (chr 207)) "\\U+1ECC" s))
  (setq s (wt3d-rep (strcat "o" (chr 249)) "\\U+00F3" s))
  (setq s (wt3d-rep (strcat "o" (chr 248)) "\\U+00F2" s))
  (setq s (wt3d-rep (strcat "o" (chr 251)) "\\U+1ECF" s))
  (setq s (wt3d-rep (strcat "o" (chr 245)) "\\U+00F5" s))
  (setq s (wt3d-rep (strcat "o" (chr 239)) "\\U+1ECD" s))
  (setq s (wt3d-rep (strcat "U" (chr 217)) "\\U+00DA" s))
  (setq s (wt3d-rep (strcat "U" (chr 216)) "\\U+00D9" s))
  (setq s (wt3d-rep (strcat "U" (chr 219)) "\\U+1EE6" s))
  (setq s (wt3d-rep (strcat "U" (chr 213)) "\\U+0168" s))
  (setq s (wt3d-rep (strcat "U" (chr 207)) "\\U+1EE4" s))
  (setq s (wt3d-rep (strcat "u" (chr 249)) "\\U+00FA" s))
  (setq s (wt3d-rep (strcat "u" (chr 248)) "\\U+00F9" s))
  (setq s (wt3d-rep (strcat "u" (chr 251)) "\\U+1EE7" s))
  (setq s (wt3d-rep (strcat "u" (chr 245)) "\\U+0169" s))
  (setq s (wt3d-rep (strcat "u" (chr 239)) "\\U+1EE5" s))
  (setq s (wt3d-rep (chr 209) "\\U+0110" s))
  (setq s (wt3d-rep (chr 241) "\\U+0111" s))
  (setq s (wt3d-rep (chr 214) "\\U+01AF" s))
  (setq s (wt3d-rep (chr 246) "\\U+01B0" s))
  (setq s (wt3d-rep (chr 212) "\\U+01A0" s))
  (setq s (wt3d-rep (chr 244) "\\U+01A1" s))
  s
)

; --- CHUYEN DOI TOAN BAN VE (HOI FONT KHONG CHAN: TAHOMA HOAC ARIAL) ---
(defun c:V2U () (c:FIXALL))
(defun c:FIXALL (/ doc cnt ss i ent obj txt new1 blks atts opt fontFile typeFace)
  (vl-load-com)
  (setq doc (vla-get-ActiveDocument (vlax-get-acad-object)))
  (princ "\n=== CHUYEN VNI SANG UNICODE KHONG CHAN ===")
  (princ "\n[1] Arial (Chuan pho thong) | [2] Tahoma (Chuan ky thuat CAD, so ro net)")
  (initget "1 2")
  (setq opt (getkword "\nChon font dich [1-Arial / 2-Tahoma] <2 - Tahoma>: "))
  (if (not opt) (setq opt "2"))
  (if (= opt "2")
    (setq fontFile "tahoma.ttf" typeFace "Tahoma")
    (setq fontFile "Arial.ttf" typeFace "Arial")
  )
  (setq cnt 0)
  ; 1. SetFont TypeFace va fontfile cho tat ca TextStyle
  (vlax-for st (vla-get-TextStyles doc)
    (vl-catch-all-apply 'vla-SetFont (list st typeFace :vlax-false :vlax-false 0 34))
    (vl-catch-all-apply 'vla-put-fontfile (list st fontFile))
    (vl-catch-all-apply 'vla-put-BigFontFile (list st ""))
  )
  ; 2. Xu ly TEXT va MTEXT
  (setq ss (ssget "_X" (list (cons 0 "TEXT,MTEXT"))))
  (if ss
    (progn
      (setq i 0)
      (while (< i (sslength ss))
        (setq ent (ssname ss i))
        (setq obj (vlax-ename->vla-object ent))
        (setq txt (vl-catch-all-apply 'vla-get-TextString (list obj)))
        (if (and txt (not (vl-catch-all-error-p txt)))
          (progn
            (setq new1 (wt3d-strip-font (wt3d-vni-convert txt)))
            (if (/= new1 txt)
              (progn (vl-catch-all-apply 'vla-put-TextString (list obj new1)) (setq cnt (1+ cnt)))
            )
          )
        )
        (setq i (1+ i))
      )
    )
  )
  ; 3. Xu ly Block Attributes
  (setq blks (ssget "_X" (list (cons 0 "INSERT"))))
  (if blks
    (progn
      (setq i 0)
      (while (< i (sslength blks))
        (setq ent (ssname blks i))
        (setq obj (vlax-ename->vla-object ent))
        (if (= (vla-get-HasAttributes obj) :vlax-true)
          (progn
            (setq atts (vlax-safearray->list (vlax-variant-value (vla-GetAttributes obj))))
            (foreach att atts
              (setq txt (vla-get-TextString att))
              (setq new1 (wt3d-strip-font (wt3d-vni-convert txt)))
              (if (/= new1 txt)
                (progn (vla-put-TextString att new1) (setq cnt (1+ cnt)))
              )
            )
          )
        )
        (setq i (1+ i))
      )
    )
  )
  (command "_.regenall")
  (princ (strcat "\n[WT3D] DA CHUYEN DOI & DONG BO " (itoa cnt) " DOI TUONG SANG UNICODE: " typeFace "!\n"))
  (princ)
)

; --- DOI FONT THEO VUNG (CAC FONT KHONG CHAN DANG DUNG) ---
(defun c:SF (/ ss opt ff sn tf doc i ent obj cnt ts ta atts tp)
  (vl-load-com)
  (setq doc (vla-get-ActiveDocument (vlax-get-acad-object)))
  (princ "\nQUET CHON DOI TUONG CHU (ENTER = chon tat ca): ")
  (setq ss (ssget (list (cons 0 "TEXT,MTEXT,INSERT"))))
  (if (not ss) (setq ss (ssget "_X" (list (cons 0 "TEXT,MTEXT,INSERT")))))
  (if (not ss) (progn (princ "\nKhong co chu nao!") (exit)))
  (princ "\n=== DANH SACH FONT KHONG CHAN (SANS-SERIF) KY THUAT ===")
  (princ "\n[1] Arial (Chuan quoc te)")
  (princ "\n[2] Tahoma (Chuan ky thuat CAD - net deu, so 0/1/8 rat ro)")
  (princ "\n[3] Segoe UI (Hien dai, sang trong)")
  (princ "\n[4] Bahnschrift (DIN 1451 - Chuan co khi Duc)")
  (princ "\n[5] VNI-Helve (Font VNI khong chan)")
  (initget "1 2 3 4 5")
  (setq opt (getkword "\nChon font [1/2/3/4/5] <2 - Tahoma>: "))
  (if (not opt) (setq opt "2"))
  (cond
    ((= opt "1") (setq ff "Arial.ttf" tf "Arial" sn "WT3D_Arial"))
    ((= opt "2") (setq ff "tahoma.ttf" tf "Tahoma" sn "WT3D_Tahoma"))
    ((= opt "3") (setq ff "segoeui.ttf" tf "Segoe UI" sn "WT3D_SegoeUI"))
    ((= opt "4") (setq ff "bahnschrift.ttf" tf "Bahnschrift" sn "WT3D_Bahnschrift"))
    ((= opt "5") (setq ff "VNI-Helve.ttf" tf "VNI-Helve" sn "WT3D_VNI_Helve"))
  )
  (setq ts (vla-get-TextStyles doc))
  (setq ta (vl-catch-all-apply 'vla-Item (list ts sn)))
  (if (vl-catch-all-error-p ta)
    (progn
      (setq ta (vla-Add ts sn))
      (vl-catch-all-apply 'vla-SetFont (list ta tf :vlax-false :vlax-false 0 34))
      (vl-catch-all-apply 'vla-put-fontfile (list ta ff))
    )
    (progn
      (vl-catch-all-apply 'vla-SetFont (list ta tf :vlax-false :vlax-false 0 34))
      (vl-catch-all-apply 'vla-put-fontfile (list ta ff))
    )
  )
  (setq cnt 0 i 0)
  (while (< i (sslength ss))
    (setq ent (ssname ss i))
    (setq obj (vlax-ename->vla-object ent))
    (setq tp (vla-get-ObjectName obj))
    (if (or (= tp "AcDbText") (= tp "AcDbMText"))
      (progn
        (vl-catch-all-apply 'vla-put-StyleName (list obj sn))
        (setq txt (vl-catch-all-apply 'vla-get-TextString (list obj)))
        (if (and txt (not (vl-catch-all-error-p txt)))
          (vl-catch-all-apply 'vla-put-TextString (list obj (wt3d-strip-font txt)))
        )
        (setq cnt (1+ cnt))
      )
    )
    (if (= tp "AcDbBlockReference")
      (if (= (vla-get-HasAttributes obj) :vlax-true)
        (progn
          (setq atts (vlax-safearray->list (vlax-variant-value (vla-GetAttributes obj))))
          (foreach att atts
            (vl-catch-all-apply 'vla-put-StyleName (list att sn))
            (setq txt (vla-get-TextString att))
            (vla-put-TextString att (wt3d-strip-font txt))
            (setq cnt (1+ cnt))
          )
        )
      )
    )
    (setq i (1+ i))
  )
  (command "_.regenall")
  (princ (strcat "\n[WT3D] DA DOI " (itoa cnt) " DOI TUONG SANG FONT KHONG CHAN: " tf "!\n"))
  (princ)
)

; Go lenh WT de mo bang dieu khien bat ky luc nao
(princ "\n[WT3D] GO LENH 'WT' DE MO BANG DIEU KHIEN!\n")
(princ)
