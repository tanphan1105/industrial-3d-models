AddReference "PresentationCore"
AddReference "WindowsBase"
AddReference "System.Drawing"
AddReference "System.Private.Windows.GdiPlus"
AddReference "System.Windows.Forms"
AddReference "System.Private.Windows.Core"

Imports System.Windows.Input
Imports Inventor
Imports System.IO

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

        Public Sub Main()
            Dim oDoc As Inventor.Document = ThisDoc.Document
            Dim oView As Inventor.View = ThisApplication.ActiveView
            Dim oCam As Inventor.Camera = oView.Camera

            If oDoc.DocumentType <> DocumentTypeEnum.kPresentationDocumentObject Then
                MessageBox.Show("File này không phải là File Phân Rã (Presentation .ipn).", "Sai Môi Trường")
                Exit Sub
            End If

            Dim baseName As String = System.IO.Path.GetFileNameWithoutExtension(oDoc.FullFileName)
            Dim masterDir As String = "d:\WT3D_Project"
            Dim savePath As String = ""

            If System.IO.Directory.Exists(masterDir & "\Preview_Image") Then
                savePath = masterDir & "\Preview_Image\" & baseName
            Else
                savePath = System.IO.Path.GetDirectoryName(oDoc.FullFileName) & "\_SEO_Images_" & baseName
            End If
            If Not System.IO.Directory.Exists(savePath) Then
                System.IO.Directory.CreateDirectory(savePath)
            End If

            Try : oDoc.ObjectVisibility.AllWorkFeatures = False : Catch : End Try

            oView.DisplayMode = DisplayModeEnum.kShadedWithEdgesRendering
            oView.ShowAmbientShadows = True
            oView.ShowObjectShadows = True 
            oView.ShowGroundShadows = True 
            oView.ShowGroundReflections = False

            ThisApplication.ColorSchemes.BackgroundType = BackgroundTypeEnum.kGradientBackgroundType

            Dim resWidth As Integer = 3840
            Dim resHeight As Integer = 2160
            Dim camW As Double
            Dim camH As Double

            oCam.Perspective = True 
            oCam.Fit()
            oCam.GetExtents(camW, camH)
            oCam.SetExtents(camW * 0.65, camH * 0.65) ' Zoom ra 65% cho khung phân rã dãn theo cụm Y
            oCam.Apply()

            Dim imgName As String = baseName & "_11_Exploded_View.png"
            Dim imgPath As String = savePath & "\" & imgName
            oCam.SaveAsBitmap(imgPath, resWidth, resHeight)

                If CheckEscape() Then
                    ThisApplication.StatusBarText = "🛑 ĐÃ DỪNG TIẾN TRÌNH THEO LỆNH (GIỮ PHÍM ESC)!"
                    Exit Sub
                End If
                SafeYield(20)

            Try
                System.GC.Collect()
                System.GC.WaitForPendingFinalizers()

                Dim tempImgPath As String = savePath & "\temp_" & imgName
                Using bmp As New System.Drawing.Bitmap(imgPath)
                    Using g As System.Drawing.Graphics = System.Drawing.Graphics.FromImage(bmp)
                        g.SmoothingMode = System.Drawing.Drawing2D.SmoothingMode.AntiAlias

                        ' ================= CENTER EMBOSS WATERMARK =================
                        g.TranslateTransform(bmp.Width / 2, bmp.Height / 2)
                        Dim mailText As String = "Industrial 3D Design by Tan Phan"
                        Using mailFont As New System.Drawing.Font("Arial", 120, System.Drawing.FontStyle.Bold)
                            Using gp As New System.Drawing.Drawing2D.GraphicsPath()
                                Dim sf As New System.Drawing.StringFormat() 
                                sf.Alignment = System.Drawing.StringAlignment.Center
                                sf.LineAlignment = System.Drawing.StringAlignment.Center
                                gp.AddString(mailText, mailFont.FontFamily, CInt(mailFont.Style), mailFont.Size, New System.Drawing.PointF(0, 0), sf)

                                Dim pThick As Single = 3 
                                Using darkPen As New System.Drawing.Pen(System.Drawing.Color.FromArgb(15, 0, 0, 0), pThick)
                                    g.TranslateTransform(4, 4)
                                    g.DrawPath(darkPen, gp)
                                    g.TranslateTransform(-4, -4)
                                End Using
                                Using lightPen As New System.Drawing.Pen(System.Drawing.Color.FromArgb(25, 255, 255, 255), pThick)
                                    g.TranslateTransform(-4, -4)
                                    g.DrawPath(lightPen, gp)
                                    g.TranslateTransform(4, 4)
                                End Using
                            End Using
                        End Using
                        g.ResetTransform()

                        ' ================= BOTTOM RIGHT B2B STAMP =================
                        Dim ratio As Single = 1.0F
                        Dim brandText As String = "WATER FILTER 3D DESIGN"
                        Dim contactText As String = "Portfolio & Custom Specs ➔ See GrabCAD Profile"

                        Using brandFont As New System.Drawing.Font("Arial Narrow", 60, System.Drawing.FontStyle.Bold)
                        Using contactFont As New System.Drawing.Font("Arial Narrow", 40, System.Drawing.FontStyle.Bold)
                            Dim brandSz As System.Drawing.SizeF = g.MeasureString(brandText, brandFont)
                            Dim contactSz As System.Drawing.SizeF = g.MeasureString(contactText, contactFont)

                            Dim maxW As Single = Math.Max(brandSz.Width, contactSz.Width)
                            Dim qrSize As Single = 200
                            Dim cPad As Single = 40
                            Dim totalW As Single = maxW + 50 + qrSize
                            Dim textBlockH As Single = brandSz.Height + contactSz.Height + 20
                            Dim totalH As Single = Math.Max(textBlockH, qrSize)

                            Dim cX As Single = bmp.Width - totalW - 80 - cPad*2
                            Dim cY As Single = bmp.Height - totalH - 80 - cPad*2

                            Dim drawRoundedRect = Sub(gfx As System.Drawing.Graphics, b As System.Drawing.Brush, p As System.Drawing.Pen, x As Single, y As Single, w As Single, h As Single, r As Single)
                                Using path As New System.Drawing.Drawing2D.GraphicsPath()
                                    path.AddArc(x, y, r, r, 180, 90)
                                    path.AddArc(x + w - r, y, r, r, 270, 90)
                                    path.AddArc(x + w - r, y + h - r, r, r, 0, 90)
                                    path.AddArc(x, y + h - r, r, r, 90, 90)
                                    path.CloseAllFigures()
                                    If b IsNot Nothing Then gfx.FillPath(b, path)
                                    If p IsNot Nothing Then gfx.DrawPath(p, path)
                                End Using
                            End Sub

                            Using bgBrush As New System.Drawing.SolidBrush(System.Drawing.Color.FromArgb(235, 52, 199, 89))
                            Using borderPen As New System.Drawing.Pen(System.Drawing.Color.FromArgb(180, 255, 255, 255), 4)
                                drawRoundedRect(g, bgBrush, borderPen, cX, cY, totalW + cPad*2, totalH + cPad*2, 40)
                            End Using
                            End Using

                            Dim currY As Single = cY + cPad + (totalH - textBlockH) / 2

                            Dim drawShadowText = Sub(txt As String, fnt As System.Drawing.Font, xPos As Single, yPos As Single, alpha As Integer)
                                Using shadowBrush As New System.Drawing.SolidBrush(System.Drawing.Color.FromArgb(50, 0, 0, 0))
                                    g.DrawString(txt, fnt, shadowBrush, xPos + 4, yPos + 4)
                                End Using
                                Using mainBrush As New System.Drawing.SolidBrush(System.Drawing.Color.FromArgb(alpha, 255, 255, 255))
                                    g.DrawString(txt, fnt, mainBrush, xPos, yPos)
                                End Using
                            End Sub

                            drawShadowText(brandText, brandFont, cX + cPad, currY, 255)
                            currY += brandSz.Height + 20
                            drawShadowText(contactText, contactFont, cX + cPad, currY, 220)

                            ' --- MÃ QR ZALO BỊ VÔ HIỆU HÓA TRONG BẢN GRABCAD ĐỂ TUÂN THỦ LUẬT CHỐNG QUẢNG CÁO ---
                        End Using
                        End Using
                    End Using
                    bmp.Save(tempImgPath, System.Drawing.Imaging.ImageFormat.Png)
                End Using

                System.IO.File.Delete(imgPath)
                System.IO.File.Move(tempImgPath, imgPath)

                oView.DisplayMode = DisplayModeEnum.kShadedWithEdgesRendering
                oView.Update()

                MessageBox.Show("Thành công xuất xưởng bản IPN số 11!", "Exploded Chamber")

            Catch ex As Exception
                MessageBox.Show("Có lỗi xử lý tem trên IPN: " & ex.Message, "Lỗi GDI+")
            End Try
            End Sub
End Class
