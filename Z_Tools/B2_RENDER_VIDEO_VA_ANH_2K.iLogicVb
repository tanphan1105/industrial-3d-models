' ==============================================================================================
' WT3D PRO ILOGIC RULE: B2_RENDER_19_IMAGES_AND_360_VIDEO - V7.0
' Tác giả: Phan Trọng Tấn - WaterTreatment3D
' ==============================================================================================

Imports System.Windows.Forms

Public Class ThisRule
    Sub Main()
        Try
            If ThisApplication.ActiveDocument Is Nothing Then
                MessageBox.Show("Vui lòng mở 1 mô hình 3D (.iam hoặc .ipt) trước khi chạy Bước này!", "WT3D Projection Engine", MessageBoxButtons.OK, MessageBoxIcon.Warning)
                Exit Sub
            End If

            Dim enginePath As String = "D:\INVENTOR_DATA\05_STANDARD_COMPONENTS\00_Standards_and_Templates\02_iLogic_Rules\WT3D_Engineering_Projection_Engine.iLogicVb"
            If Not System.IO.File.Exists(enginePath) Then
                enginePath = "D:\WT3D_Project\Z_Tools\WT3D_Engineering_Projection_Engine.iLogicVb"
            End If

            iLogicVb.Automation.RunExternalRule(ThisApplication.ActiveDocument, enginePath)
        Catch ex As Exception
            MessageBox.Show("Lỗi thực thi Projection Engine: " & ex.Message, "Báo Động WT3D B2 Render")
        End Try
    End Sub
End Class
