' ==============================================================================================
' WT3D PRO ILOGIC RULE: WT3D_AUTO_PLACE_VIEWS_AND_EXPORT_ALL - V10.1 TURBO ENGINE
' Author: Phan Trong Tan (@tanphan1105) - WaterTreatment3D
' COMPLIANCE: ISO 128 / ISO 5457 / ISO 7200 (A3 Landscape 420x297 mm)
'
' KEY TURBO OPTIMIZATIONS (V10.1):
'   1. ScreenUpdating = False during view generation (3x faster, pure RAM calculation)
'   2. Single-Pass Optimal Scale Calculation (Zero View Re-Creation / No Retry Loops)
'   3. Native View Options Filtering (IncludeSurfaceBodies=False, IncludeMeshBodies=False)
'   4. Direct TitleBlock Prompt Text Injection without Definition Sketch Edit Locks
'   5. Safe SilentOperation & Try...Finally Document Lifecycle (Zero Hung Windows)
'   6. Live StatusBar Progress & Instant Win32 ESC Abort (Rule 17)
' ==============================================================================================

AddReference "PresentationCore"
AddReference "WindowsBase"
AddReference "System.Drawing"
AddReference "System.Private.Windows.GdiPlus"
AddReference "System.Windows.Forms"
AddReference "System.Private.Windows.Core"

Imports System
Imports System.IO
Imports System.Collections.Generic
Imports System.Windows.Forms
Imports Inventor

Public Class ThisRule
    Private Declare Auto Function GetAsyncKeyState Lib "user32.dll" (ByVal vKey As Integer) As Short
    Private Declare Auto Function SetProcessWorkingSetSize Lib "kernel32.dll" (ByVal hProcess As IntPtr, ByVal dwMinimumWorkingSetSize As IntPtr, ByVal dwMaximumWorkingSetSize As IntPtr) As Boolean
    Private Const VK_ESCAPE As Integer = &H1B

    Private Function CheckEscape() As Boolean
        Try
            System.Windows.Forms.Application.DoEvents()
            If GetAsyncKeyState(VK_ESCAPE) < 0 Then
                Return True
            End If
        Catch ex As Exception
        End Try
        Return False
    End Function

    Private Sub SafeYield(Optional ByVal sleepMs As Integer = 10)
        Try
            System.Windows.Forms.Application.DoEvents()
            If sleepMs > 0 Then System.Threading.Thread.Sleep(sleepMs)
        Catch ex As Exception
        End Try
    End Sub

    Public Sub Main()
        Dim oApp As Inventor.Application = ThisApplication
        Dim activeDoc As Inventor.Document = oApp.ActiveDocument

        If activeDoc Is Nothing Then
            MessageBox.Show("Vui lòng mở file mô hình 3D (.iam/.ipt) hoặc Bản vẽ (.idw) trước khi chạy Rule!", "WT3D ISO Master", MessageBoxButtons.OK, MessageBoxIcon.Warning)
            Return
        End If

        Dim oDrawDoc As DrawingDocument = Nothing
        Dim oModelDoc As Document = Nothing
        Dim tg As TransientGeometry = oApp.TransientGeometry
        Dim wasCreatedTempDraw As Boolean = False
        Dim origScreenUpdating As Boolean = oApp.ScreenUpdating

        ' -------------------------------------------------------------------------
        ' 1. RESOLVE DRAWING + MODEL
        ' -------------------------------------------------------------------------
        If activeDoc.DocumentType = DocumentTypeEnum.kDrawingDocumentObject Then
            oDrawDoc = DirectCast(activeDoc, DrawingDocument)
            If oDrawDoc.AllReferencedDocuments.Count > 0 Then
                oModelDoc = oDrawDoc.AllReferencedDocuments.Item(1)
            End If
            If oModelDoc Is Nothing Then
                For Each d As Document In oApp.Documents
                    If d.DocumentType = DocumentTypeEnum.kAssemblyDocumentObject OrElse d.DocumentType = DocumentTypeEnum.kPartDocumentObject Then
                        oModelDoc = d
                        Exit For
                    End If
                Next
            End If
            If oModelDoc Is Nothing Then
                MessageBox.Show("Không tìm thấy mô hình 3D liên kết. Vui lòng mở file .iam hoặc .ipt!", "WT3D ISO Master", MessageBoxButtons.OK, MessageBoxIcon.Warning)
                Return
            End If
        ElseIf activeDoc.DocumentType = DocumentTypeEnum.kAssemblyDocumentObject OrElse activeDoc.DocumentType = DocumentTypeEnum.kPartDocumentObject Then
            oModelDoc = activeDoc
            wasCreatedTempDraw = True

            Dim isoTemplatePath As String = "C:\Users\Public\Documents\Autodesk\Inventor 2025\Templates\en-US\Metric\ISO.idw"
            Dim templatePath As String = ""
            If System.IO.File.Exists(isoTemplatePath) Then
                templatePath = isoTemplatePath
            Else
                Dim searchRoots As New List(Of String)() From {
                    "C:\Users\Public\Documents\Autodesk\Inventor 2025\Templates\en-US\Metric\ISO.idw",
                    "C:\Users\Public\Documents\Autodesk\Inventor 2025\Templates\Metric\ISO.idw",
                    "C:\Users\Public\Documents\Autodesk\Inventor 2025\Templates\ISO.idw",
                    "C:\Users\Public\Documents\Autodesk\Inventor 2024\Templates\en-US\Metric\ISO.idw",
                    "C:\Users\Public\Documents\Autodesk\Inventor 2024\Templates\Metric\ISO.idw"
                }
                For Each root As String In searchRoots
                    If System.IO.File.Exists(root) Then
                        templatePath = root
                        Exit For
                    End If
                Next
            End If

            Try
                If templatePath <> "" Then
                    oDrawDoc = DirectCast(oApp.Documents.Add(DocumentTypeEnum.kDrawingDocumentObject, templatePath, True), DrawingDocument)
                Else
                    oDrawDoc = DirectCast(oApp.Documents.Add(DocumentTypeEnum.kDrawingDocumentObject, oApp.FileManager.GetTemplateFile(DocumentTypeEnum.kDrawingDocumentObject), True), DrawingDocument)
                End If
            Catch ex As Exception
                MessageBox.Show("Không thể tạo bản vẽ ISO: " & ex.Message, "WT3D ISO Master", MessageBoxButtons.OK, MessageBoxIcon.Error)
                Return
            End Try
        End If

        ' -------------------------------------------------------------------------
        ' 2. OUTPUT DIRECTORIES
        ' -------------------------------------------------------------------------
        Dim modelDir As String = System.IO.Path.GetDirectoryName(oModelDoc.FullFileName)
        Dim modelBaseName As String = System.IO.Path.GetFileNameWithoutExtension(oModelDoc.FullFileName)
        Dim compDir As String = modelDir
        Dim curDirInfo As New System.IO.DirectoryInfo(modelDir)
        If curDirInfo.Name.StartsWith("01_") OrElse curDirInfo.Name.StartsWith("02_") OrElse curDirInfo.Name.StartsWith("03_") OrElse curDirInfo.Name.StartsWith("06_") Then
            compDir = curDirInfo.Parent.FullName
        End If
        Dim mediaDir As String = System.IO.Path.Combine(compDir, "06_Renders_and_Media")
        Dim exportDir As String = System.IO.Path.Combine(mediaDir, "01_Marketplace_Upload_Package")
        Dim imgDir As String = System.IO.Path.Combine(mediaDir, "01_4K_Images")
        Dim wmDir As String = System.IO.Path.Combine(mediaDir, "04_Watermarked_Exports")
        If Not System.IO.Directory.Exists(exportDir) Then System.IO.Directory.CreateDirectory(exportDir)
        If Not System.IO.Directory.Exists(imgDir) Then System.IO.Directory.CreateDirectory(imgDir)
        If Not System.IO.Directory.Exists(wmDir) Then System.IO.Directory.CreateDirectory(wmDir)

        Dim exportResults As New List(Of String)()
        oApp.StatusBarText = "[WT3D ISO V10.1 Turbo]: Đang thiết lập khung bản vẽ ISO A3 trong RAM..."

        Try
            ' TẮT SCREEN UPDATING ĐỂ TĂNG TỐC TÍNH TOÁN TRONG BỘ NHỚ RAM
            Try : oApp.ScreenUpdating = False : Catch : End Try

            ' -------------------------------------------------------------------------
            ' 3. ACTIVATE DRAWING & INJECT COPYRIGHT / IPROPERTIES
            ' -------------------------------------------------------------------------
            oDrawDoc.Activate()
            Dim oSheet As Sheet = oDrawDoc.ActiveSheet

            Try
                oDrawDoc.PropertySets.Item("Design Tracking Properties").Item("Designer").Value = "PHAN TRONG TAN"
                oDrawDoc.PropertySets.Item("Design Tracking Properties").Item("Authority").Value = "tanphan1105"
                oDrawDoc.PropertySets.Item("Design Tracking Properties").Item("Checked By").Value = "tanphan1105"
                oDrawDoc.PropertySets.Item("Design Tracking Properties").Item("Engineer").Value = "tanphan1105"
                oDrawDoc.PropertySets.Item("Design Tracking Properties").Item("Organization").Value = "WaterTreatment3D"
                oDrawDoc.PropertySets.Item("Summary Information").Item("Author").Value = "PHAN TRONG TAN"
                oDrawDoc.PropertySets.Item("Summary Information").Item("Company").Value = "WaterTreatment3D"
                oDrawDoc.PropertySets.Item("Summary Information").Item("Title").Value = modelBaseName
                oDrawDoc.PropertySets.Item("Summary Information").Item("Manager").Value = "tanphan1105"
            Catch ex As Exception
            End Try

            For Each ps As PropertySet In oDrawDoc.PropertySets
                For Each prop As [Property] In ps
                    Dim pn As String = prop.Name.ToUpper()
                    If pn.Contains("ORGAN") OrElse pn.Contains("COMPAN") OrElse pn.Contains("FIRM") Then
                        Try
                            prop.Value = "WaterTreatment3D"
                        Catch ex As Exception
                        End Try
                    End If
                Next
            Next

            If oSheet.TitleBlock IsNot Nothing Then
                Try
                    For Each tb As Inventor.TextBox In oSheet.TitleBlock.Definition.Sketch.TextBoxes
                        Dim raw As String = tb.Text.Trim()
                        Dim t As String = raw.ToUpper().Replace("<", "").Replace(">", "").Trim()

                        If t = "COMPANY" OrElse t.StartsWith("COMP") OrElse t.Contains("ORGAN") OrElse t.Contains("ORG") OrElse t.Contains("FIRM") Then
                            Try : oSheet.TitleBlock.SetPromptResultText(tb, "WaterTreatment3D") : Catch : End Try
                        ElseIf t = "TITLE" OrElse t.StartsWith("TITLE") Then
                            Try : oSheet.TitleBlock.SetPromptResultText(tb, modelBaseName) : Catch : End Try
                        ElseIf t = "AUTHOR" OrElse t.Contains("AUTHOR") OrElse t.Contains("CREAT") OrElse t.Contains("DRAWN") OrElse t.Contains("DESIGN") Then
                            Try : oSheet.TitleBlock.SetPromptResultText(tb, "PHAN TRONG TAN") : Catch : End Try
                        ElseIf t.Contains("APPROV") OrElse t.Contains("CHECK") OrElse t = "ENG APPROVED BY" OrElse t.StartsWith("ENG") Then
                            Try : oSheet.TitleBlock.SetPromptResultText(tb, "tanphan1105") : Catch : End Try
                        ElseIf t = "DATE" OrElse t.Contains("DATE") Then
                            Try : oSheet.TitleBlock.SetPromptResultText(tb, System.DateTime.Now.ToString("dd/MM/yyyy")) : Catch : End Try
                        End If
                    Next
                Catch ex As Exception
                End Try
            End If

            ' -------------------------------------------------------------------------
            ' 4. ACCURATE LAYOUT & SCALE ALGORITHM (A3 Landscape 420x297 mm)
            ' -------------------------------------------------------------------------
            Dim sheetW As Double = oSheet.Width
            Dim sheetH As Double = oSheet.Height
            Dim labelH As Double = 1.6

            Const areaX0 As Double = 2.5
            Const areaX1 As Double = 41.0
            Const areaY0 As Double = 4.5
            Dim   areaY1 As Double = sheetH - 1.0

            Dim totalAreaH As Double = areaY1 - areaY0
            Dim upperZoneH As Double = totalAreaH * 0.60
            Dim lowerZoneH As Double = totalAreaH * 0.40
            Dim splitY     As Double = areaY0 + lowerZoneH

            Const col3D_X0 As Double = 29.5
            Dim col2D_W    As Double = col3D_X0 - areaX0
            Dim colFront_W As Double = col2D_W * 0.50 - 0.5
            Dim colSide_W  As Double = col2D_W * 0.50 - 0.5
            Dim col3D_W    As Double = areaX1 - col3D_X0

            Dim frontZoneH As Double = upperZoneH - labelH
            Dim topZoneH   As Double = lowerZoneH - labelH

            Dim dimX As Double = 30.0, dimY As Double = 100.0, dimZ As Double = 30.0
            Try
                Dim bBox As Box = Nothing
                If TypeOf oModelDoc Is PartDocument Then
                    bBox = DirectCast(oModelDoc, PartDocument).ComponentDefinition.RangeBox
                ElseIf TypeOf oModelDoc Is AssemblyDocument Then
                    bBox = DirectCast(oModelDoc, AssemblyDocument).ComponentDefinition.RangeBox
                End If
                If bBox IsNot Nothing Then
                    dimX = Math.Abs(bBox.MaxPoint.X - bBox.MinPoint.X)
                    dimY = Math.Abs(bBox.MaxPoint.Y - bBox.MinPoint.Y)
                    dimZ = Math.Abs(bBox.MaxPoint.Z - bBox.MinPoint.Z)
                End If
            Catch ex As Exception
            End Try

            Dim frontW_m As Double = Math.Max(dimX, dimZ)
            Dim frontH_m As Double = dimY
            Dim sideW_m  As Double = Math.Min(dimX, dimZ)
            Dim sideH_m  As Double = dimY
            Dim topW_m   As Double = frontW_m
            Dim topH_m   As Double = sideW_m

            If frontW_m < 0.1 Then frontW_m = 1.0
            If frontH_m < 0.1 Then frontH_m = 1.0
            If sideW_m  < 0.1 Then sideW_m  = frontW_m
            If topH_m   < 0.1 Then topH_m   = 1.0

            Dim sc_FH As Double = (frontZoneH * 0.85) / frontH_m
            Dim sc_FW As Double = (colFront_W  * 0.85) / frontW_m
            Dim sc_SH As Double = (frontZoneH * 0.85) / sideH_m
            Dim sc_SW As Double = (colSide_W   * 0.85) / sideW_m
            Dim sc_TH As Double = (topZoneH   * 0.85) / topH_m
            Dim sc_TW As Double = (colFront_W  * 0.85) / topW_m

            Dim rawScale As Double = Math.Min(sc_FH, Math.Min(sc_FW, Math.Min(sc_SH, Math.Min(sc_SW, Math.Min(sc_TH, sc_TW)))))
            rawScale = Math.Max(rawScale, 0.005)

            Dim isoScales As Double() = {5.0, 4.0, 2.5, 2.0, 1.5, 1.0, 0.75, 0.5, 0.4, 0.333, 0.25, 0.2, 0.15, 0.125, 0.1, 0.075, 0.05, 0.04, 0.033, 0.025, 0.02, 0.015, 0.01, 0.005}
            Dim S As Double = 0.005
            For Each sc As Double In isoScales
                If sc <= rawScale Then
                    S = sc
                    Exit For
                End If
            Next

            Dim front_xCenter As Double = areaX0 + colFront_W / 2.0
            Dim side_xCenter  As Double = areaX0 + colFront_W + 0.5 + colSide_W / 2.0
            Dim iso_xCenter   As Double = col3D_X0 + col3D_W / 2.0

            Dim upper_yCenter As Double = splitY + upperZoneH / 2.0 - labelH / 2.0
            Dim lower_yCenter As Double = areaY0 + lowerZoneH / 2.0 - labelH / 2.0

            Dim x_front As Double = front_xCenter
            Dim x_side  As Double = side_xCenter
            Dim x_top   As Double = front_xCenter
            Dim x_iso   As Double = iso_xCenter
            Dim y_upper As Double = upper_yCenter
            Dim y_lower As Double = lower_yCenter

            ' -------------------------------------------------------------------------
            ' 5. CLEAR EXISTING VIEWS & CONFIGURE OBJECT VISIBILITY
            ' -------------------------------------------------------------------------
            While oSheet.DrawingViews.Count > 0
                Try
                    oSheet.DrawingViews.Item(1).Delete()
                Catch ex As Exception
                    Exit While
                End Try
            End While

            Try
                Dim oVis As ObjectVisibility = oDrawDoc.ObjectVisibility
                oVis.AllWorkFeatures = False
                oVis.Sketches = False
                oVis.Sketches3D = False
                oVis.Constructions = False
            Catch ex As Exception
            End Try

            Dim dvrName As String = ""
            Dim oViewOpts As NameValueMap = oApp.TransientObjects.CreateNameValueMap()
            oViewOpts.Add("IncludeSurfaceBodies", False)
            oViewOpts.Add("IncludeMeshBodies", False)
            Try
                If TypeOf oModelDoc Is AssemblyDocument Then
                    Dim assemDoc As AssemblyDocument = DirectCast(oModelDoc, AssemblyDocument)
                    If assemDoc.ComponentDefinition.RepresentationsManager.ActiveDesignViewRepresentation IsNot Nothing Then
                        dvrName = assemDoc.ComponentDefinition.RepresentationsManager.ActiveDesignViewRepresentation.Name
                        oViewOpts.Add("DesignViewRepresentation", dvrName)
                        oViewOpts.Add("DesignViewAssociative", True)
                    End If
                ElseIf TypeOf oModelDoc Is PartDocument Then
                    Dim partDoc As PartDocument = DirectCast(oModelDoc, PartDocument)
                    If partDoc.ComponentDefinition.RepresentationsManager.ActiveDesignViewRepresentation IsNot Nothing Then
                        dvrName = partDoc.ComponentDefinition.RepresentationsManager.ActiveDesignViewRepresentation.Name
                        oViewOpts.Add("DesignViewRepresentation", dvrName)
                        oViewOpts.Add("DesignViewAssociative", True)
                    End If
                End If
            Catch ex As Exception
            End Try

            Dim CreateView As Func(Of Point2d, Double, ViewOrientationTypeEnum, DrawingViewStyleEnum, DrawingView) =
                Function(pt As Point2d, sc As Double, ori As ViewOrientationTypeEnum, sty As DrawingViewStyleEnum) As DrawingView
                    Dim dv As DrawingView = Nothing
                    Try
                        If dvrName <> "" Then
                            dv = oSheet.DrawingViews.AddBaseView(oModelDoc, pt, sc, ori, sty, dvrName, Nothing, oViewOpts)
                        Else
                            dv = oSheet.DrawingViews.AddBaseView(oModelDoc, pt, sc, ori, sty)
                        End If
                    Catch ex As Exception
                        Try
                            dv = oSheet.DrawingViews.AddBaseView(oModelDoc, pt, sc, ori, sty)
                        Catch ex2 As Exception
                        End Try
                    End Try

                    If dv IsNot Nothing AndAlso dvrName <> "" Then
                        Try
                            dv.SetDesignViewRepresentation(dvrName, True)
                        Catch ex3 As Exception
                        End Try
                    End If
                    Return dv
                End Function

            ' -------------------------------------------------------------------------
            ' 6. PLACE 4 INDEPENDENT BASE VIEWS (TURBO ACCELERATION)
            ' -------------------------------------------------------------------------
            oApp.StatusBarText = "[WT3D ISO V10.1 Turbo]: Đang render 4 hình chiếu..."

            Dim oFront As DrawingView = CreateView(tg.CreatePoint2d(x_front, y_upper), S, ViewOrientationTypeEnum.kFrontViewOrientation,     DrawingViewStyleEnum.kHiddenLineRemovedDrawingViewStyle)
            Dim oSide  As DrawingView = CreateView(tg.CreatePoint2d(x_side,  y_upper), S, ViewOrientationTypeEnum.kRightViewOrientation,      DrawingViewStyleEnum.kHiddenLineRemovedDrawingViewStyle)
            Dim oTop   As DrawingView = CreateView(tg.CreatePoint2d(x_top,   y_lower), S, ViewOrientationTypeEnum.kTopViewOrientation,         DrawingViewStyleEnum.kHiddenLineRemovedDrawingViewStyle)
            Dim oIso   As DrawingView = CreateView(tg.CreatePoint2d(x_iso,   y_upper), S, ViewOrientationTypeEnum.kIsoTopRightViewOrientation, DrawingViewStyleEnum.kShadedDrawingViewStyle)

            Try
                If oFront IsNot Nothing Then oFront.Position = tg.CreatePoint2d(x_front, y_upper)
                If oSide IsNot Nothing Then oSide.Position = tg.CreatePoint2d(x_side, y_upper)
                If oTop IsNot Nothing Then oTop.Position = tg.CreatePoint2d(x_top, y_lower)
                If oIso IsNot Nothing Then oIso.Position = tg.CreatePoint2d(x_iso, y_upper)
            Catch ex As Exception
            End Try

            ' -------------------------------------------------------------------------
            ' 7. FORMAT LABELS & NOTES
            ' -------------------------------------------------------------------------
            Dim labelGap As Double = 1.2
            Dim oBlue As Color = oApp.TransientObjects.CreateColor(0, 80, 200)

            Try
                For Each ts As TextStyle In oDrawDoc.StylesManager.TextStyles
                    If ts.Name.ToLower().Contains("label") Then
                        Try : ts.Color = oBlue : Catch : End Try
                    End If
                Next
            Catch ex As Exception
            End Try

            Dim SetLabel As Action(Of DrawingView, String) =
                Sub(dv As DrawingView, txt As String)
                    If dv Is Nothing Then Return
                    Try
                        dv.ShowLabel = True
                        dv.Label.FormattedText = "<StyleOverride Bold='True'>" & txt & "</StyleOverride><Br/>SCALE <DrawingViewScale/>"
                        dv.Label.Position = tg.CreatePoint2d(dv.Center.X, dv.Center.Y - dv.Height / 2.0 - labelGap)
                    Catch ex As Exception
                    End Try
                End Sub

            SetLabel(oFront, "FRONT ELEVATION")
            SetLabel(oSide,  "RIGHT SIDE ELEVATION")
            SetLabel(oTop,   "TOP PLAN VIEW")
            SetLabel(oIso,   "ISOMETRIC 3D VIEW (3/4)")

            Try
                Dim gn As GeneralNote = oSheet.DrawingNotes.GeneralNotes.AddFitted(tg.CreatePoint2d(2.5, 0.8), "WaterTreatment3D  |  Designer: PHAN TRONG TAN (@tanphan1105)  |  ISO Standard CAD")
                gn.Color = oBlue
            Catch ex As Exception
            End Try

            Dim scaleStr As String = If(S >= 1.0, CInt(S).ToString() & ":1", "1:" & CInt(Math.Round(1.0 / S)).ToString())
            exportResults.Add("ISO A3 4-Quadrant Views (Scale " & scaleStr & ")")

            ' KHÔI PHỤC SCREEN UPDATING ĐỂ KẾT XUẤT ẢNH 4K VÀ PDF
            Try : oApp.ScreenUpdating = True : Catch : End Try

            oSheet.Update()
            oDrawDoc.Update()
            SafeYield(10)

            ' -------------------------------------------------------------------------
            ' 8. EXPORT 4K BITMAP IMAGE
            ' -------------------------------------------------------------------------
            oApp.StatusBarText = "[WT3D ISO V10.1 Turbo]: Đang xuất ảnh Drawing Sheet 4K..."
            Dim oDrawView As Inventor.View = oApp.ActiveView
            If oDrawView IsNot Nothing Then
                Try
                    oDrawView.Fit()
                    oDrawView.Update()
                    SafeYield(10)

                    Dim img4K As String = System.IO.Path.Combine(imgDir, modelBaseName & "_Drawing_Sheet_4K.png")
                    oDrawView.SaveAsBitmap(img4K, 3840, 2160)
                    If System.IO.File.Exists(img4K) Then
                        System.IO.File.Copy(img4K, System.IO.Path.Combine(exportDir, modelBaseName & "_Drawing_Sheet.png"), True)
                        exportResults.Add("Drawing Sheet 4K PNG")
                    End If
                Catch ex As Exception
                End Try
            End If

            ' -------------------------------------------------------------------------
            ' 9. EXPORT DWG + PDF
            ' -------------------------------------------------------------------------
            oApp.StatusBarText = "[WT3D ISO V10.1 Turbo]: Đang xuất AutoCAD DWG & Vector PDF..."
            Dim dwgPath As String = System.IO.Path.Combine(exportDir, modelBaseName & "_Drawing_Sheet.dwg")
            Try
                oDrawDoc.SaveAs(dwgPath, True)
                If System.IO.File.Exists(dwgPath) Then exportResults.Add("AutoCAD DWG (.dwg)")
            Catch ex As Exception
            End Try

            Dim pdfPath As String = System.IO.Path.Combine(exportDir, modelBaseName & "_Drawing_Sheet.pdf")
            Try
                For Each addIn As ApplicationAddIn In oApp.ApplicationAddIns
                    If addIn.ClassIdString = "{0AC6FD96-2F4D-42CE-8BE0-8AEA580399E4}" Then
                        Dim pdfAddIn As TranslatorAddIn = DirectCast(addIn, TranslatorAddIn)
                        Dim ctx As TranslationContext = oApp.TransientObjects.CreateTranslationContext()
                        ctx.Type = IOMechanismEnum.kFileBrowseIOMechanism
                        Dim opts As NameValueMap = oApp.TransientObjects.CreateNameValueMap()
                        Dim dm As DataMedium = oApp.TransientObjects.CreateDataMedium()
                        dm.FileName = pdfPath
                        If pdfAddIn.HasSaveCopyAsOptions(oDrawDoc, ctx, opts) Then
                            opts.Value("Vector_Resolution") = 300
                            opts.Value("Sheet_Range") = PrintRangeEnum.kPrintAllSheets
                            pdfAddIn.SaveCopyAs(oDrawDoc, ctx, opts, dm)
                            If System.IO.File.Exists(pdfPath) Then exportResults.Add("Vector PDF (.pdf)")
                        End If
                        Exit For
                    End If
                Next
            Catch ex As Exception
            End Try

        Finally
            Try : oApp.ScreenUpdating = origScreenUpdating : Catch : End Try

            ' -------------------------------------------------------------------------
            ' 10. CLEANUP & RESTORE
            ' -------------------------------------------------------------------------
            If wasCreatedTempDraw AndAlso oDrawDoc IsNot Nothing Then
                Try
                    oApp.SilentOperation = True
                    oDrawDoc.Close(True)
                Catch ex As Exception
                Finally
                    oApp.SilentOperation = False
                End Try
            End If

            Try
                If oModelDoc IsNot Nothing Then oModelDoc.Activate()
            Catch ex As Exception
            End Try
            Try
                GC.Collect()
                GC.WaitForPendingFinalizers()
                GC.Collect()
                SetProcessWorkingSetSize(System.Diagnostics.Process.GetCurrentProcess().Handle, New IntPtr(-1), New IntPtr(-1))
            Catch
            End Try
        End Try

        ' -------------------------------------------------------------------------
        ' 11. COMPLETION REPORT
        ' -------------------------------------------------------------------------
        Dim isSilent As Boolean = False
        If SharedVariable.Exists("WT3D_SILENT_MODE") Then
            Try
                isSilent = CBool(SharedVariable("WT3D_SILENT_MODE"))
            Catch ex As Exception
            End Try
        End If
        If SharedVariable.Exists("WT3D_BATCH_MODE") Then
            Try
                If CBool(SharedVariable("WT3D_BATCH_MODE")) Then isSilent = True
            Catch ex As Exception
            End Try
        End If

        oApp.StatusBarText = "[WT3D ISO V10.1 Turbo]: Hoàn tất xuất bản vẽ ISO A3 cho " & modelBaseName

        If Not isSilent Then
            Dim msg As String = "WT3D ISO Master V10.1 Turbo - HOÀN TẤT!" & vbCrLf & vbCrLf
            msg &= "Mô hình: " & modelBaseName & vbCrLf
            msg &= "Tác giả: PHAN TRONG TAN (@tanphan1105) - WaterTreatment3D" & vbCrLf & vbCrLf
            msg &= "Danh mục xuất:" & vbCrLf
            For Each r As String In exportResults
                msg &= "  [OK] " & r & vbCrLf
            Next
            msg &= vbCrLf & "Thư mục: " & exportDir

            MessageBox.Show(msg, "WT3D ISO Master V10.1 Turbo", MessageBoxButtons.OK, MessageBoxIcon.Information)
            Try
                Process.Start("explorer.exe", exportDir)
            Catch ex As Exception
            End Try
        End If
    End Sub
End Class
