' ==============================================================================
' NIGHT-CRAWLER EXPLODED CINEMATIC ENGINE
' Tool: Bấm 1 phát chụp ảnh rã rác (Exploded View) siêu nét 4K + Tiêm Bản quyền
' Tích hợp: Trợ lý gọi ngầm hộp thoại Publish Video của Inventor
' Đảm bảo: Dùng trên file Presentation (.ipn)
' ==============================================================================

AddReference "PresentationCore"
AddReference "WindowsBase"
AddReference "System.Drawing"
AddReference "System.Private.Windows.GdiPlus"
AddReference "System.Windows.Forms"
AddReference "System.Private.Windows.Core"

Imports System
Imports System.IO
Imports System.Drawing
Imports System.Drawing.Drawing2D
Imports System.Drawing.Imaging

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Try
            Dim oDoc As Document = ThisApplication.ActiveDocument
            If oDoc.DocumentType <> DocumentTypeEnum.kPresentationDocumentObject Then
                MessageBox.Show("Síp ơi! Giao thức này chỉ dành để chụp ảnh Tháo Ráp cho file .ipn (Presentation) thôi nha!", "Cảnh Báo An Toàn")
                Exit Sub
            End If

            ' Format Tên File
            Dim fName As String = System.IO.Path.GetFileNameWithoutExtension(oDoc.FullFileName)
            Dim saveDir As String = "d:\WT3D_Project\Preview_Image\" & fName
            If Not System.IO.Directory.Exists(saveDir) Then
                System.IO.Directory.CreateDirectory(saveDir)
            End If

            Dim imgFile As String = saveDir & "\" & fName & "_11_Exploded_Hero.png"
            If System.IO.File.Exists(imgFile) Then System.IO.File.Delete(imgFile)

            ' Tối ưu màn hình chụp
            Dim oView As View = ThisApplication.ActiveView
            oView.DisplayMode = DisplayModeEnum.kShadedRendering ' Tắt viền nét đứt cho sang trọng
            oView.Update()

            ' Chụp khung hình siêu nét 4K
            oView.Camera.SaveAsBitmap(imgFile, 3840, 2160)

            ' ==================================================================
            ' ĐÓNG DẤU BẢN QUYỀN (APPLE GREEN B2B STANDARD)
            ' ==================================================================
            Try
                Dim tempImgPath As String = saveDir & "\" & fName & "_Exploded_Temp.png"
                Using bmp As New System.Drawing.Bitmap(imgFile)
                    Using g As System.Drawing.Graphics = System.Drawing.Graphics.FromImage(bmp)
                        g.SmoothingMode = System.Drawing.Drawing2D.SmoothingMode.AntiAlias
                        g.TextRenderingHint = System.Drawing.Text.TextRenderingHint.AntiAlias

                        Dim brandText As String = "WATER FILTER 3D DESIGN"
                        Dim brandFont As New System.Drawing.Font("Arial Narrow", 45, System.Drawing.FontStyle.Bold)
                        Dim contactText As String = "Portfolio & Custom Specs ➔ See GrabCAD Profile"
                        Dim contactFont As New System.Drawing.Font("Arial Narrow", 30, System.Drawing.FontStyle.Bold)

                        Dim brandSz As System.Drawing.SizeF = g.MeasureString(brandText, brandFont)
                        Dim contactSz As System.Drawing.SizeF = g.MeasureString(contactText, contactFont)

                        Dim maxW As Single = Math.Max(brandSz.Width, contactSz.Width)
                        Dim qrSize As Single = 150
                        Dim cPad As Single = 30

                        Dim totalW As Single = maxW + 50 + qrSize
                        Dim textBlockH As Single = brandSz.Height + contactSz.Height + 20
                        Dim totalH As Single = Math.Max(textBlockH, qrSize)

                        Dim cX As Single = bmp.Width - totalW - 60 - cPad * 2
                        Dim cY As Single = bmp.Height - totalH - 60 - cPad * 2

                        Dim drawRoundedRect = Sub(grp As System.Drawing.Graphics, b As System.Drawing.Brush, p As System.Drawing.Pen, x As Single, y As Single, w As Single, h As Single, r As Single)
                            Using path As New System.Drawing.Drawing2D.GraphicsPath()
                                path.AddArc(x, y, r, r, 180, 90)
                                path.AddArc(x + w - r, y, r, r, 270, 90)
                                path.AddArc(x + w - r, y + h - r, r, r, 0, 90)
                                path.AddArc(x, y + h - r, r, r, 90, 90)
                                path.CloseAllFigures()
                                grp.FillPath(b, path)
                                grp.DrawPath(p, path)
                            End Using
                        End Sub

                        Using bgBrush As New System.Drawing.SolidBrush(System.Drawing.Color.FromArgb(235, 52, 199, 89))
                        Using borderPen As New System.Drawing.Pen(System.Drawing.Color.FromArgb(180, 255, 255, 255), 4)
                            drawRoundedRect(g, bgBrush, borderPen, cX, cY, totalW + cPad*2, totalH + cPad*2, 40)
                        End Using
                        End Using

                        Dim currY As Single = cY + cPad + (totalH - textBlockH) / 2

                        Dim drawShadowText = Sub(txt As String, fnt As System.Drawing.Font, xPos As Single, yPos As Single, alpha As Integer)
                            Using shadowBrush As New System.Drawing.SolidBrush(System.Drawing.Color.FromArgb(50, 0, 0, 0))
                                g.DrawString(txt, fnt, shadowBrush, xPos + 4, yPos + 4)
                            End Using
                            Using mainBrush As New System.Drawing.SolidBrush(System.Drawing.Color.FromArgb(alpha, 255, 255, 255))
                                g.DrawString(txt, fnt, mainBrush, xPos, yPos)
                            End Using
                        End Sub

                        drawShadowText(brandText, brandFont, cX + cPad, currY, 255)
                        currY += brandSz.Height + 20
                        drawShadowText(contactText, contactFont, cX + cPad, currY, 220)

                        ' --- MÃ QR ZALO BỊ VÔ HIỆU HÓA TRONG BẢN GRABCAD ĐỂ TUÂN THỦ LUẬT CHỐNG QUẢNG CÁO ---
                    End Using
                    bmp.Save(tempImgPath, System.Drawing.Imaging.ImageFormat.Png)
                End Using

                System.IO.File.Delete(imgFile)
                System.IO.File.Move(tempImgPath, imgFile)
            Catch ex As Exception
            End Try

            ' =======================================================
            ' TIÊM BẢN QUYỀN PNG EXIF 
            ' =======================================================
            Try
                Dim exifScript As String = "d:\WT3D_Project\Z_Tools\Auto_SEO_Exif_Burner_GrabCAD.ps1"
                If System.IO.File.Exists(exifScript) Then
                    Dim psCmd As String = "powershell -ExecutionPolicy Bypass -WindowStyle Hidden -File """ & exifScript & """ -targetDir """ & saveDir & """"
                    Microsoft.VisualBasic.Interaction.Shell(psCmd, AppWinStyle.Hide, False)
                End If
            Catch ex As Exception : End Try

            oView.DisplayMode = DisplayModeEnum.kShadedWithEdgesRendering
            oView.Update()

            ' =======================================================
            ' KẾT THÚC VÀ BÁO CÁO
            ' =======================================================
            MessageBox.Show("Mục tiêu rã xác đã bị tiêu diệt!" & vbCrLf & "Ảnh 4K bọc Bản Quyền đã được lưu chuẩn SEO vào: " & vbCrLf & saveDir, "Sniper Shot 4K Tĩnh")
            Try : System.Diagnostics.Process.Start("explorer.exe", saveDir) : Catch : End Try

        Catch ex As Exception
            MessageBox.Show("Lỗi rã đồ: " & ex.Message, "Cảnh báo An Toàn")
        End Try
    End Sub
End Class
