AddReference "PresentationCore"
AddReference "WindowsBase"
AddReference "System.Drawing"
AddReference "System.Private.Windows.GdiPlus"
AddReference "System.Windows.Forms"
AddReference "System.Private.Windows.Core"

Imports System.Windows.Forms

Public Class ThisRule
    Private Declare Auto Function GetAsyncKeyState Lib "user32.dll" (ByVal vKey As Integer) As Short
    Private Const VK_ESCAPE As Integer = &H1B

    Private Function CheckEscapeKey() As Boolean
        Try
            System.Windows.Forms.Application.DoEvents()
            If GetAsyncKeyState(&H1B) < 0 Then
                SharedVariable("WT3D_ABORT_REQUESTED") = True
                Return True
            End If
            If SharedVariable.Exists("WT3D_ABORT_REQUESTED") Then
                If CBool(SharedVariable("WT3D_ABORT_REQUESTED")) Then Return True
            End If
            Return False
        Catch
            Return False
        End Try
    End Function

    Sub Main()
    Try : SharedVariable("WT3D_ABORT_REQUESTED") = False : Catch : End Try
    Try : GetAsyncKeyState(&H1B) : Catch : End Try
Dim oApp  As Inventor.Application = ThisApplication
Dim oDoc  As Inventor.Document    = oApp.ActiveDocument

If oDoc Is Nothing OrElse (oDoc.DocumentType <> DocumentTypeEnum.kAssemblyDocumentObject AndAlso oDoc.DocumentType <> DocumentTypeEnum.kPartDocumentObject) Then
    MessageBox.Show("Vui lòng mở một mô hình 3D (.iam hoặc .ipt) trước khi chạy!", "WT3D", MessageBoxButtons.OK, MessageBoxIcon.Warning)
    Exit Sub
End If

' ==============================================================================
' DỌN DẸP HIỂN THỊ TRIỆT ĐỂ 100% NGAY TỪ ĐẦU (TẮT TOÀN BỘ MẶT PHẲNG, TRỤC, SKETCH)
' ==============================================================================
Try
    ' 1. ÉP TẮT QUA ĐIỀU KHIỂN HỆ THỐNG COMMANDMANAGER CỦA INVENTOR (TƯƠNG ĐƯƠNG BẤM TẮT TRÊN GIAO DIỆN)
    Try
        Dim ctrlDef As ControlDefinition = ThisApplication.CommandManager.ControlDefinitions.Item("AppAllWorkFeaturesCmd")
        If ctrlDef IsNot Nothing AndAlso ctrlDef.Pressed Then
            ctrlDef.Execute()
        End If
    Catch : End Try

    ' 2. Tắt toàn bộ Work Features ở cấp View & Tài liệu
    oDoc.ObjectVisibility.AllWorkFeatures = False
    oDoc.ObjectVisibility.UserWorkPlanes = False
    oDoc.ObjectVisibility.OriginWorkPlanes = False
    oDoc.ObjectVisibility.UserWorkAxes = False
    oDoc.ObjectVisibility.OriginWorkAxes = False
    oDoc.ObjectVisibility.UserWorkPoints = False
    oDoc.ObjectVisibility.OriginWorkPoints = False
    oDoc.ObjectVisibility.OriginWorkFeatures = False
    oDoc.ObjectVisibility.Sketches = False
    oDoc.ObjectVisibility.Sketches3D = False
    oDoc.ObjectVisibility.WeldmentSymbols = False
    oDoc.ObjectVisibility.ConstructionSurfaces = False

    ' 3. Quét đệ quy từng Part con để ép Visible = False cho toàn bộ WorkPlanes / WorkAxes
    If TypeOf oDoc Is AssemblyDocument Then
        Dim oAsmDoc As AssemblyDocument = DirectCast(oDoc, AssemblyDocument)
        For Each wp As WorkPlane In oAsmDoc.ComponentDefinition.WorkPlanes
            Try : wp.Visible = False : Catch : End Try
        Next
        For Each wa As WorkAxis In oAsmDoc.ComponentDefinition.WorkAxes
            Try : wa.Visible = False : Catch : End Try
        Next
        For Each wpnt As WorkPoint In oAsmDoc.ComponentDefinition.WorkPoints
            Try : wpnt.Visible = False : Catch : End Try
        Next
        For Each occ As ComponentOccurrence In oAsmDoc.ComponentDefinition.Occurrences
            If Not occ.Suppressed Then
                Try
                    If occ.DefinitionDocumentType = DocumentTypeEnum.kPartDocumentObject Then
                        Dim pDef As PartComponentDefinition = DirectCast(occ.Definition, PartComponentDefinition)
                        For Each wp As WorkPlane In pDef.WorkPlanes
                            Try : wp.Visible = False : Catch : End Try
                        Next
                        For Each wa As WorkAxis In pDef.WorkAxes
                            Try : wa.Visible = False : Catch : End Try
                        Next
                        For Each wpnt As WorkPoint In pDef.WorkPoints
                            Try : wpnt.Visible = False : Catch : End Try
                        Next
                    ElseIf occ.DefinitionDocumentType = DocumentTypeEnum.kAssemblyDocumentObject Then
                        Dim subAsmDef As AssemblyComponentDefinition = DirectCast(occ.Definition, AssemblyComponentDefinition)
                        For Each wp As WorkPlane In subAsmDef.WorkPlanes
                            Try : wp.Visible = False : Catch : End Try
                        Next
                        For Each subOcc As ComponentOccurrence In subAsmDef.Occurrences
                            If Not subOcc.Suppressed AndAlso subOcc.DefinitionDocumentType = DocumentTypeEnum.kPartDocumentObject Then
                                Dim subPDef As PartComponentDefinition = DirectCast(subOcc.Definition, PartComponentDefinition)
                                For Each wp As WorkPlane In subPDef.WorkPlanes
                                    Try : wp.Visible = False : Catch : End Try
                                Next
                            End If
                        Next
                    End If
                Catch : End Try
            End If
        Next
    ElseIf TypeOf oDoc Is PartDocument Then
        Dim oPartDoc As PartDocument = DirectCast(oDoc, PartDocument)
        For Each wp As WorkPlane In oPartDoc.ComponentDefinition.WorkPlanes
            Try : wp.Visible = False : Catch : End Try
        Next
        For Each wa As WorkAxis In oPartDoc.ComponentDefinition.WorkAxes
            Try : wa.Visible = False : Catch : End Try
        Next
        For Each wpnt As WorkPoint In oPartDoc.ComponentDefinition.WorkPoints
            Try : wpnt.Visible = False : Catch : End Try
        Next
    End If

    oApp.ActiveView.Update()
Catch : End Try

' ==============================================================================
' SECTION 0: BẢNG ĐIỀU KHIỂN CHỌN CHẾ ĐỘ RENDER (INTERACTIVE GUI DIALOG)
' ==============================================================================
Dim isVertical As Boolean = True
Dim is2K       As Boolean = False
Dim is4K       As Boolean = False
Dim isOpenFolder As Boolean = True
Dim useKeyShotLighting As Boolean = False
Dim postureMode As Integer = 0 ' 0: Cân Đối (Default), 1: Nằm Ngang, 2: Cao Đứng

Dim isBatchAuto As Boolean = False
If SharedVariable.Exists("WT3D_BATCH_MODE") Then
    Try : isBatchAuto = CBool(SharedVariable("WT3D_BATCH_MODE")) : Catch : End Try
End If

If isBatchAuto Then
    isVertical = False
    is2K = True
    is4K = False
Else
    Using frm As New System.Windows.Forms.Form()
        frm.Text = "🎬 WT3D Projection Studio - Thiết Lập Xuất Video & Bản Vẽ"
        frm.Size = New System.Drawing.Size(480, 640)
        frm.StartPosition = System.Windows.Forms.FormStartPosition.CenterScreen
        frm.FormBorderStyle = System.Windows.Forms.FormBorderStyle.FixedDialog
        frm.MaximizeBox = False
        frm.MinimizeBox = False
        frm.BackColor = System.Drawing.Color.FromArgb(248, 249, 252)
        frm.Font = New System.Drawing.Font("Segoe UI", 9.5F, System.Drawing.FontStyle.Regular)
        
        ' Tiêu đề Header
        Dim lblTitle As New System.Windows.Forms.Label()
        lblTitle.Text = "📐 THIẾT LẬP RENDER MÔ HÌNH 3D"
        lblTitle.Font = New System.Drawing.Font("Segoe UI", 12.0F, System.Drawing.FontStyle.Bold)
        lblTitle.ForeColor = System.Drawing.Color.FromArgb(10, 45, 120)
        lblTitle.Location = New System.Drawing.Point(25, 12)
        lblTitle.AutoSize = True
        frm.Controls.Add(lblTitle)
        
        ' GroupBox 1: Khung Hình (Ngang / Dọc)
        Dim grpOrientation As New System.Windows.Forms.GroupBox()
        grpOrientation.Text = " 📱 Định Dạng Khung Hình "
        grpOrientation.Location = New System.Drawing.Point(25, 42)
        grpOrientation.Size = New System.Drawing.Size(415, 80)
        
        Dim radVertical As New System.Windows.Forms.RadioButton()
        radVertical.Text = "📱 DỌC 9:16 (Shorts / TikTok / Reels / Mobile)"
        radVertical.Location = New System.Drawing.Point(20, 22)
        radVertical.AutoSize = True
        radVertical.Checked = False
        radVertical.Font = New System.Drawing.Font("Segoe UI", 9.5F, System.Drawing.FontStyle.Bold)
        grpOrientation.Controls.Add(radVertical)
        
        Dim radLandscape As New System.Windows.Forms.RadioButton()
        radLandscape.Text = "🖥️ NGANG 16:9 (YouTube / Website / B2B Catalog)"
        radLandscape.Location = New System.Drawing.Point(20, 48)
        radLandscape.AutoSize = True
        radLandscape.Checked = True
        grpOrientation.Controls.Add(radLandscape)
        frm.Controls.Add(grpOrientation)
        
        ' Tự động nhận diện Dự án lớn hay Linh kiện tiêu chuẩn để đặt mặc định
        Dim isComponent As Boolean = False
        If oDoc.FullFileName.ToLower().Contains("05_standard_components") OrElse oDoc.FullFileName.ToLower().EndsWith(".ipt") Then
            isComponent = True
        End If

        ' Tự động nhận diện tỷ lệ dáng máy (Nằm ngang / Cân đối / Cao đứng) để gợi ý góc quay
        Dim autoDetectedPosture As Integer = 0 ' 0: Cân đối, 1: Nằm ngang, 2: Cao đứng
        Try
            Dim preDef As ComponentDefinition = oDoc.ComponentDefinition
            If preDef IsNot Nothing AndAlso preDef.RangeBox IsNot Nothing Then
                Dim preRb As Box = preDef.RangeBox
                Dim pDx As Double = Math.Abs(preRb.MaxPoint.X - preRb.MinPoint.X)
                Dim pDy As Double = Math.Abs(preRb.MaxPoint.Y - preRb.MinPoint.Y)
                Dim pDz As Double = Math.Abs(preRb.MaxPoint.Z - preRb.MinPoint.Z)
                Dim pMaxH As Double = Math.Max(pDx, pDz)
                If pMaxH > 0.1 Then
                    Dim rAspect As Double = pDy / pMaxH
                    If rAspect < 0.6 Then
                        autoDetectedPosture = 1 ' Nằm ngang
                    ElseIf rAspect > 1.6 Then
                        autoDetectedPosture = 2 ' Cao đứng
                    Else
                        autoDetectedPosture = 0 ' Cân đối
                    End If
                End If
            End If
        Catch : End Try

        ' GroupBox 2: Độ Phân Giải (HD / 2K / 4K)
        Dim grpQuality As New System.Windows.Forms.GroupBox()
        grpQuality.Text = " 💎 Độ Phân Giải & Tốc Độ "
        grpQuality.Location = New System.Drawing.Point(25, 128)
        grpQuality.Size = New System.Drawing.Size(415, 105)
        
        Dim radHD As New System.Windows.Forms.RadioButton()
        radHD.Text = "⚡ Full HD 1080p (Mặc Định Linh Kiện • Nhanh ~25s)"
        radHD.Location = New System.Drawing.Point(20, 22)
        radHD.AutoSize = True
        radHD.Checked = isComponent
        radHD.Font = New System.Drawing.Font("Segoe UI", 9.5F, System.Drawing.FontStyle.Bold)
        grpQuality.Controls.Add(radHD)
        
        Dim rad2K As New System.Windows.Forms.RadioButton()
        rad2K.Text = "✨ 2K QHD 1440p (Mặc Định Dự Án Hệ Thống • Chuẩn Sàn 3D)"
        rad2K.Location = New System.Drawing.Point(20, 48)
        rad2K.AutoSize = True
        rad2K.Checked = Not isComponent
        rad2K.Font = New System.Drawing.Font("Segoe UI", 9.5F, System.Drawing.FontStyle.Bold)
        grpQuality.Controls.Add(rad2K)
        
        Dim rad4K As New System.Windows.Forms.RadioButton()
        rad4K.Text = "💎 Ultra HD 4K (Chất Lượng Tối Thượng • Siêu Nét Bán Sàn)"
        rad4K.Location = New System.Drawing.Point(20, 74)
        rad4K.AutoSize = True
        grpQuality.Controls.Add(rad4K)
        frm.Controls.Add(grpQuality)
        
        ' GroupBox 3: Dáng Mô Hình & Góc Quay Camera
        Dim grpPosture As New System.Windows.Forms.GroupBox()
        grpPosture.Text = " 📐 Dáng Mô Hình & Góc Quay Camera "
        grpPosture.Location = New System.Drawing.Point(25, 240)
        grpPosture.Size = New System.Drawing.Size(415, 115)
        
        Dim radPostureStandard As New System.Windows.Forms.RadioButton()
        radPostureStandard.Text = "⚖️ Dáng Cân Đối (+15°/+18° • Hệ bồn, máy bơm, tủ điện)" & If(autoDetectedPosture = 0, " ⭐ [Gợi Ý]", "")
        radPostureStandard.Location = New System.Drawing.Point(20, 24)
        radPostureStandard.AutoSize = True
        radPostureStandard.Checked = (autoDetectedPosture = 0)
        radPostureStandard.Font = New System.Drawing.Font("Segoe UI", 9.5F, If(autoDetectedPosture = 0, System.Drawing.FontStyle.Bold, System.Drawing.FontStyle.Regular))
        radPostureStandard.ForeColor = If(autoDetectedPosture = 0, System.Drawing.Color.FromArgb(10, 45, 120), System.Drawing.Color.Black)
        grpPosture.Controls.Add(radPostureStandard)
        
        Dim radPostureHorizontal As New System.Windows.Forms.RadioButton()
        radPostureHorizontal.Text = "🛹 Dáng Nằm Ngang (+26°/+30° • Skid RO bẹt, bồn ngang)" & If(autoDetectedPosture = 1, " ⭐ [Gợi Ý]", "")
        radPostureHorizontal.Location = New System.Drawing.Point(20, 52)
        radPostureHorizontal.AutoSize = True
        radPostureHorizontal.Checked = (autoDetectedPosture = 1)
        radPostureHorizontal.Font = New System.Drawing.Font("Segoe UI", 9.5F, If(autoDetectedPosture = 1, System.Drawing.FontStyle.Bold, System.Drawing.FontStyle.Regular))
        radPostureHorizontal.ForeColor = If(autoDetectedPosture = 1, System.Drawing.Color.FromArgb(10, 45, 120), System.Drawing.Color.Black)
        grpPosture.Controls.Add(radPostureHorizontal)
        
        Dim radPostureTower As New System.Windows.Forms.RadioButton()
        radPostureTower.Text = "🗼 Dáng Cao Đứng (+10°/+12° • Cột composite, tháp đứng)" & If(autoDetectedPosture = 2, " ⭐ [Gợi Ý]", "")
        radPostureTower.Location = New System.Drawing.Point(20, 80)
        radPostureTower.AutoSize = True
        radPostureTower.Checked = (autoDetectedPosture = 2)
        radPostureTower.Font = New System.Drawing.Font("Segoe UI", 9.5F, If(autoDetectedPosture = 2, System.Drawing.FontStyle.Bold, System.Drawing.FontStyle.Regular))
        radPostureTower.ForeColor = If(autoDetectedPosture = 2, System.Drawing.Color.FromArgb(10, 45, 120), System.Drawing.Color.Black)
        grpPosture.Controls.Add(radPostureTower)
        frm.Controls.Add(grpPosture)
        
        ' GroupBox 4: Chế Độ Ánh Sáng
        Dim grpLight As New System.Windows.Forms.GroupBox()
        grpLight.Text = " 🌟 Chế Độ Ánh Sáng & Môi Trường "
        grpLight.Location = New System.Drawing.Point(25, 362)
        grpLight.Size = New System.Drawing.Size(415, 82)
        
        Dim radLightKeyShot As New System.Windows.Forms.RadioButton()
        radLightKeyShot.Text = "🌟 4-Point KeyShot Studio Rig (Tự Động Viền Sáng & Bóng)"
        radLightKeyShot.Location = New System.Drawing.Point(20, 24)
        radLightKeyShot.AutoSize = True
        radLightKeyShot.Checked = False
        radLightKeyShot.Font = New System.Drawing.Font("Segoe UI", 9.5F, System.Drawing.FontStyle.Bold)
        radLightKeyShot.ForeColor = System.Drawing.Color.FromArgb(10, 110, 60)
        grpLight.Controls.Add(radLightKeyShot)
        
        Dim radLightUser As New System.Windows.Forms.RadioButton()
        radLightUser.Text = "🎨 Giữ Nguyên Tùy Chỉnh Của Tôi (Đèn, Shadow, Môi trường)"
        radLightUser.Location = New System.Drawing.Point(20, 50)
        radLightUser.AutoSize = True
        radLightUser.Checked = True
        radLightUser.Font = New System.Drawing.Font("Segoe UI", 9.5F, System.Drawing.FontStyle.Bold)
        radLightUser.ForeColor = System.Drawing.Color.FromArgb(20, 70, 160)
        grpLight.Controls.Add(radLightUser)
        frm.Controls.Add(grpLight)

        ' Checkbox Mở thư mục
        Dim chkOpenFolder As New System.Windows.Forms.CheckBox()
        chkOpenFolder.Text = "📂 Tự động mở thư mục ảnh & video sau khi hoàn tất"
        chkOpenFolder.Location = New System.Drawing.Point(30, 456)
        chkOpenFolder.AutoSize = True
        chkOpenFolder.Checked = True
        chkOpenFolder.Font = New System.Drawing.Font("Segoe UI", 9.0F, System.Drawing.FontStyle.Italic)
        frm.Controls.Add(chkOpenFolder)

        ' Nút Bắt Đầu
        Dim btnRun As New System.Windows.Forms.Button()
        btnRun.Text = "🚀 BẮT ĐẦU RENDER"
        btnRun.Location = New System.Drawing.Point(200, 492)
        btnRun.Size = New System.Drawing.Size(240, 45)
        btnRun.BackColor = System.Drawing.Color.FromArgb(10, 110, 60)
        btnRun.ForeColor = System.Drawing.Color.White
        btnRun.Font = New System.Drawing.Font("Segoe UI", 10.5F, System.Drawing.FontStyle.Bold)
        btnRun.FlatStyle = System.Windows.Forms.FlatStyle.Flat
        btnRun.DialogResult = System.Windows.Forms.DialogResult.OK
        frm.Controls.Add(btnRun)
        
        ' Nút Hủy
        Dim btnCancel As New System.Windows.Forms.Button()
        btnCancel.Text = "HỦY"
        btnCancel.Location = New System.Drawing.Point(25, 492)
        btnCancel.Size = New System.Drawing.Size(160, 45)
        btnCancel.BackColor = System.Drawing.Color.FromArgb(225, 230, 240)
        btnCancel.ForeColor = System.Drawing.Color.FromArgb(60, 70, 85)
        btnCancel.FlatStyle = System.Windows.Forms.FlatStyle.Flat
        btnCancel.DialogResult = System.Windows.Forms.DialogResult.Cancel
        frm.Controls.Add(btnCancel)
        
        frm.AcceptButton = btnRun
        frm.CancelButton = btnCancel
        
        Dim dr As System.Windows.Forms.DialogResult = frm.ShowDialog()
        If dr <> System.Windows.Forms.DialogResult.OK Then
            Exit Sub
        End If
        
        isVertical = radVertical.Checked
        is2K = rad2K.Checked
        is4K = rad4K.Checked
        isOpenFolder = chkOpenFolder.Checked
        useKeyShotLighting = radLightKeyShot.Checked
        
        If radPostureHorizontal.Checked Then
            postureMode = 1
        ElseIf radPostureTower.Checked Then
            postureMode = 2
        Else
            postureMode = 0
        End If
    End Using
End If
If useKeyShotLighting Then
    ' ==============================================================================
    ' ⚡ KHÓA CỨNG TWO LIGHTS + ALL SHADOWS + ABOVE NGAY KHI BẤM NÚT (INSTANT ON-CLICK)
    ' ==============================================================================
    Try
        Dim isPartDoc As Boolean = (TypeOf oDoc Is PartDocument)
        Dim isAsmDoc As Boolean = (TypeOf oDoc Is AssemblyDocument)
        Dim oStyles As LightingStyles = Nothing
        If isPartDoc Then
            oStyles = CType(oDoc, PartDocument).LightingStyles
        ElseIf isAsmDoc Then
            oStyles = CType(oDoc, AssemblyDocument).LightingStyles
        End If

        Dim targetLs As LightingStyle = Nothing
        If oStyles IsNot Nothing Then
            Try : targetLs = oStyles.Item("Two Lights") : Catch : End Try
            If targetLs Is Nothing Then
                For Each ls As LightingStyle In oStyles
                    If ls.Name.Equals("Two Lights", StringComparison.OrdinalIgnoreCase) Then
                        targetLs = ls : Exit For
                    End If
                Next
            End If
            If targetLs Is Nothing Then
                For Each ls As LightingStyle In oStyles
                    If ls.Name.ToLower().Contains("two") OrElse ls.Name.Contains("2") Then
                        targetLs = ls : Exit For
                    End If
                Next
            End If

            If targetLs IsNot Nothing Then
                Try
                    If targetLs.StyleLocation = StyleLocationEnum.kLibraryStyleLocation Then
                        targetLs.ConvertToLocal()
                    End If
                Catch : End Try

                If isPartDoc Then
                    CType(oDoc, PartDocument).ActiveLightingStyle = targetLs
                ElseIf isAsmDoc Then
                    CType(oDoc, AssemblyDocument).ActiveLightingStyle = targetLs
                End If
            End If
        End If

        Dim curStyle As LightingStyle = Nothing
        If isPartDoc Then
            curStyle = CType(oDoc, PartDocument).ActiveLightingStyle
        ElseIf isAsmDoc Then
            curStyle = CType(oDoc, AssemblyDocument).ActiveLightingStyle
        End If

        If curStyle IsNot Nothing Then
            Try : curStyle.ShadowDirection = ShadowDirectionEnum.kAboveShadowDirection : Catch : End Try
            Try : curStyle.Brightness = 0.83 : Catch : End Try
            Try : curStyle.Ambience = 0.27 : Catch : End Try
            Try : curStyle.ShadowDensity = 0.48 : Catch : End Try
            Dim lNum As Integer = 1
            For Each lt As Light In curStyle.Lights
                If lNum = 1 Then
                    Try : lt.On = True : Catch : End Try
                    Try : lt.Color = ThisApplication.TransientObjects.CreateColor(255, 255, 255) : Catch : End Try
                    Try : lt.Intensity = 1.0 : Catch : End Try
                    Try : lt.Direction = ThisApplication.TransientGeometry.CreateVector(-0.651641, -0.453990, -0.607665) : Catch : End Try
                ElseIf lNum = 2 Then
                    Try : lt.On = True : Catch : End Try
                    Try : lt.Color = ThisApplication.TransientObjects.CreateColor(255, 255, 255) : Catch : End Try
                    Try : lt.Intensity = 0.87 : Catch : End Try
                    Try : lt.Direction = ThisApplication.TransientGeometry.CreateVector(-0.598518, 0.104528, -0.794261) : Catch : End Try
                Else
                    Try : lt.On = False : Catch : End Try
                End If
                lNum += 1
            Next
        End If

        ' Bật All Shadows & Cập nhật View tức thì
        Dim curView As Inventor.View = ThisApplication.ActiveView
        If curView IsNot Nothing Then
            Try : curView.DisplayMode = DisplayModeEnum.kShadedWithEdgesRendering : Catch : End Try
            Try : curView.ShowGroundShadows = True : Catch : End Try
            Try : curView.ShowAmbientShadows = True : Catch : End Try
            Try : curView.ShowObjectShadows = True : Catch : End Try
            Try : curView.ShowGroundReflections = True : Catch : End Try
            Try
                Dim oCamPersp As Camera = curView.Camera
                If Not oCamPersp.Perspective Then
                    oCamPersp.Perspective = True
                    oCamPersp.ApplyWithoutTransition()
                End If
            Catch : End Try
            Try : curView.Update() : Catch : End Try
        End If
        Try : oDoc.Update() : Catch : End Try
    Catch : End Try



End If


' ==============================================================================
' SECTION 1: CẤU HÌNH THÔNG SỐ ĐỘ PHÂN GIẢI & KHUNG HÌNH
' ==============================================================================
Dim CFG_FPS     As Integer = 30      ' 30 fps tiêu chuẩn
Dim CFG_RenderW As Integer = 1080
Dim CFG_RenderH As Integer = 1920
Dim modeTag     As String  = "9x16_Portrait"
Dim qualityTag  As String  = "1080p_FHD"
Dim fullTag     As String  = "9x16_Portrait_1080p"
Dim snapshotSubDir As String = "9_16_Portrait_1080p"

If isVertical Then
    If is4K Then
        CFG_RenderW = 2160 : CFG_RenderH = 3840
        modeTag = "9x16_Portrait" : qualityTag = "4K_UHD" : fullTag = "9x16_Portrait_4K" : snapshotSubDir = "9_16_Portrait_4K"
    ElseIf is2K Then
        CFG_RenderW = 1440 : CFG_RenderH = 2560
        modeTag = "9x16_Portrait" : qualityTag = "2K_QHD" : fullTag = "9x16_Portrait_2K" : snapshotSubDir = "9_16_Portrait_2K"
    Else
        CFG_RenderW = 1080 : CFG_RenderH = 1920
        modeTag = "9x16_Portrait" : qualityTag = "1080p_FHD" : fullTag = "9x16_Portrait_1080p" : snapshotSubDir = "9_16_Portrait_1080p"
    End If
Else
    If is4K Then
        CFG_RenderW = 3840 : CFG_RenderH = 2160
        modeTag = "16x9_Landscape" : qualityTag = "4K_UHD" : fullTag = "16x9_Landscape_4K" : snapshotSubDir = "16_9_Landscape_4K"
    ElseIf is2K Then
        CFG_RenderW = 2560 : CFG_RenderH = 1440
        modeTag = "16x9_Landscape" : qualityTag = "2K_QHD" : fullTag = "16x9_Landscape_2K" : snapshotSubDir = "16_9_Landscape_2K"
    Else
        CFG_RenderW = 1920 : CFG_RenderH = 1080
        modeTag = "16x9_Landscape" : qualityTag = "1080p_FHD" : fullTag = "16x9_Landscape_1080p" : snapshotSubDir = "16_9_Landscape_1080p"
    End If
End If

Dim fIntro  As Integer = 90   ' Số frame Cảnh đầu: Xoay 3/4 DƯỚI 360 độ (3.0 giây - Siêu mượt mà)
Dim fFlight As Integer = 28   ' Số frame chuyển động bay (0.95 giây - Lướt êm ái)
Dim fHold   As Integer = 45   ' Số frame khóa mặt chiếu 2D (1.5 giây - Đọc rõ kích thước L, W, H)
Dim fOutro  As Integer = 75   ' Số frame Cảnh cuối: Xoay 3/4 TRÊN (2.5 giây - Bao quát siêu mượt mà)
Dim fFinale As Integer = 45   ' Số frame CHỐT CẢNH FIT TO VIEW VIEWCUBE (1.5 giây - Giữ tĩnh)

Dim CFG_FitPadding As Double = 0.72 ' Tỷ lệ 72% (chừa lề 14% cho đường kích thước CAD)

Dim oView As Inventor.View        = oApp.ActiveView
Dim oCam  As Inventor.Camera      = oView.Camera
Dim tg    As TransientGeometry    = oApp.TransientGeometry

' ==============================================================================
' SECTION 2: LƯU TRẠNG THÁI GỐC
' ==============================================================================
Dim orgEyeX As Double = oCam.Eye.X, orgEyeY As Double = oCam.Eye.Y, orgEyeZ As Double = oCam.Eye.Z
Dim orgTgtX As Double = oCam.Target.X, orgTgtY As Double = oCam.Target.Y, orgTgtZ As Double = oCam.Target.Z
Dim orgUpX  As Double = oCam.UpVector.X, orgUpY  As Double = oCam.UpVector.Y, orgUpZ  As Double = oCam.UpVector.Z
Dim orgPersp As Boolean = oCam.Perspective
Dim orgPerspAng As Double = 0.52
Try : orgPerspAng = oCam.PerspectiveAngle : Catch : End Try
Dim orgDispMode As DisplayModeEnum = oView.DisplayMode
Dim orgAmbient As Boolean = oView.ShowAmbientShadows
Dim orgObject As Boolean = oView.ShowObjectShadows
Dim orgGround As Boolean = oView.ShowGroundShadows

' ==============================================================================
' SECTION 3: TÍNH TOÁN KÍCH THƯỚC PHỦ BÌ (BOUNDING BOX & DIMENSIONS IN MM)
' ==============================================================================
Dim rb As Box = Nothing
Try : rb = oDoc.ComponentDefinition.RangeBox : Catch : End Try
Dim minX_init As Double = 0, minY_init As Double = 0, minZ_init As Double = 0
Dim maxX_init As Double = 100, maxY_init As Double = 100, maxZ_init As Double = 100

If rb IsNot Nothing AndAlso rb.MinPoint IsNot Nothing AndAlso rb.MaxPoint IsNot Nothing Then
    minX_init = rb.MinPoint.X : minY_init = rb.MinPoint.Y : minZ_init = rb.MinPoint.Z
    maxX_init = rb.MaxPoint.X : maxY_init = rb.MaxPoint.Y : maxZ_init = rb.MaxPoint.Z
Else
    Try
        oCam.Fit()
        oCam.ApplyWithoutTransition()
        Dim extW As Double, extH As Double
        oCam.GetExtents(extW, extH)
        minX_init = -extW / 2 : maxX_init = extW / 2
        minY_init = 0 : maxY_init = extH
        minZ_init = -extW / 2 : maxZ_init = extW / 2
    Catch : End Try
End If

Dim cx As Double = (minX_init + maxX_init) / 2.0
Dim cy As Double = (minY_init + maxY_init) / 2.0
Dim cz As Double = (minZ_init + maxZ_init) / 2.0
Dim dx As Double = Math.Max(0.1, maxX_init - minX_init)
Dim dy As Double = Math.Max(0.1, maxY_init - minY_init)
Dim dz As Double = Math.Max(0.1, maxZ_init - minZ_init)

' ==============================================================================
' CẤU HÌNH GÓC QUAY & ĐỘ LỆCH SHIFTY THEO DÁNG MÔ HÌNH (POSTURE ADAPTIVE RIG)
' ==============================================================================
Dim elevAngle_Bottom As Double
Dim elevAngle_Top    As Double
Dim shiftY           As Double
Dim heroDistFactor   As Double
Dim cubeZoomFactor   As Double
Dim targetFillV      As Double
Dim targetFillH      As Double = If(isVertical, 0.88, 0.92)

Select Case postureMode
    Case 1 ' DÁNG NẰM NGANG / SKID BẸT (+26° / +30°)
        elevAngle_Bottom = 0.45 ' ~26 độ (góc cao chúc xuống bao quát toàn bộ mặt sàn thiết bị)
        elevAngle_Top    = 0.52 ' ~30 độ (toàn cảnh mặt trên)
        shiftY           = dy * 0.10 ' Dịch tâm camera xuống 10% chiều cao để mô hình nổi lên trên
        heroDistFactor   = If(isVertical, 0.72, 0.55)
        cubeZoomFactor   = If(isVertical, 0.60, 0.45)
        targetFillV      = If(isVertical, 0.85, 0.82)
        
    Case 2 ' DÁNG CAO ĐỨNG / CỘT THÁP (+10° / +12°)
        elevAngle_Bottom = 0.17 ' ~10 độ (ngang ngực / ngước lên nhẹ, tôn vinh dáng đứng cao lớn)
        elevAngle_Top    = 0.21 ' ~12 độ (chống méo đỉnh tháp)
        shiftY           = dy * 0.04 ' Tháp cao chỉ cần dịch nhẹ 4%
        heroDistFactor   = If(isVertical, 0.70, 0.50)
        cubeZoomFactor   = If(isVertical, 0.55, 0.40)
        targetFillV      = If(isVertical, 0.88, 0.85)
        
    Case Else ' DÁNG CÂN ĐỐI TIÊU CHUẨN (+15° / +18°)
        elevAngle_Bottom = 0.26 ' ~15 độ (3/4 trên kinh điển)
        elevAngle_Top    = 0.32 ' ~18 độ (bao quát toàn cảnh)
        shiftY           = dy * 0.07 ' Dịch tâm camera xuống 7% để chân đế thông thoáng
        heroDistFactor   = If(isVertical, 0.72, 0.53)
        cubeZoomFactor   = If(isVertical, 0.58, 0.43)
        targetFillV      = If(isVertical, 0.85, 0.82)
End Select

Dim targetY As Double = cy - shiftY

' Kích thước phủ bì chính xác theo Milimét (1 cm trong Inventor = 10 mm)
Dim dx_mm As Long = CLng(Math.Round(dx * 10.0))
Dim dy_mm As Long = CLng(Math.Round(dy * 10.0))
Dim dz_mm As Long = CLng(Math.Round(dz * 10.0))

Dim aspect As Double = CDbl(CFG_RenderW) / CDbl(CFG_RenderH)
Dim maxHoriz As Double = Math.Max(dx, dz)
Dim maxDim As Double = Math.Max(maxHoriz * 1.77, dy)
Dim camDist As Double = maxDim * 1.40

' ==============================================================================
' LẤY TỌA ĐỘ VÀ VECTOR CHUẨN XÁC 100% TRỰC TIẾP DỰA THEO VIEWCUBE CỦA INVENTOR
' ==============================================================================
Dim origCam As Camera = oView.Camera

' 0. VIEWCUBE ISO TOP RIGHT (Khảo sát góc nhìn kinh điển từ ViewCube & Phóng to cận cảnh)
origCam.ViewOrientationType = ViewOrientationTypeEnum.kIsoTopRightViewOrientation
origCam.Perspective = True
origCam.PerspectiveAngle = 0.52
origCam.Fit()
origCam.ApplyWithoutTransition()

Dim rawFitEye As Point = origCam.Eye
Dim fitCubeTgt As Point = origCam.Target
Dim fitCubeUp  As UnitVector = origCam.UpVector

' Phóng to mô hình to lớn, bề thế và dịch lên trên để lộ rõ chân đế (theo cubeZoomFactor và shiftY)
Dim vEyeTgt As Vector = tg.CreateVector(rawFitEye.X - fitCubeTgt.X, rawFitEye.Y - fitCubeTgt.Y, rawFitEye.Z - fitCubeTgt.Z)
Dim fitCubeEye As Point = tg.CreatePoint(
    fitCubeTgt.X + vEyeTgt.X * cubeZoomFactor,
    fitCubeTgt.Y + vEyeTgt.Y * cubeZoomFactor - shiftY,
    fitCubeTgt.Z + vEyeTgt.Z * cubeZoomFactor
)
fitCubeTgt = tg.CreatePoint(fitCubeTgt.X, fitCubeTgt.Y - shiftY, fitCubeTgt.Z)

' 1. FRONT VIEW TỪ VIEWCUBE (Nhân cự ly camDist chống dính góc 3D)
origCam.ViewOrientationType = ViewOrientationTypeEnum.kFrontViewOrientation
origCam.Fit()
origCam.ApplyWithoutTransition()
Dim vFront As Vector = tg.CreateVector(origCam.Eye.X - cx, origCam.Eye.Y - cy, origCam.Eye.Z - cz)
vFront.Normalize()
Dim frontEye As Point = tg.CreatePoint(cx + vFront.X * camDist, cy + vFront.Y * camDist, cz + vFront.Z * camDist)
Dim frontUp  As UnitVector = origCam.UpVector

' 2. TOP VIEW TỪ VIEWCUBE (Nhân cự ly camDist)
origCam.ViewOrientationType = ViewOrientationTypeEnum.kTopViewOrientation
origCam.Fit()
origCam.ApplyWithoutTransition()
Dim vTop As Vector = tg.CreateVector(origCam.Eye.X - cx, origCam.Eye.Y - cy, origCam.Eye.Z - cz)
vTop.Normalize()
Dim topEye As Point = tg.CreatePoint(cx + vTop.X * camDist, cy + vTop.Y * camDist, cz + vTop.Z * camDist)
Dim topUp  As UnitVector = origCam.UpVector

' 3. RIGHT VIEW TỪ VIEWCUBE (Nhân cự ly camDist)
origCam.ViewOrientationType = ViewOrientationTypeEnum.kRightViewOrientation
origCam.Fit()
origCam.ApplyWithoutTransition()
Dim vRight As Vector = tg.CreateVector(origCam.Eye.X - cx, origCam.Eye.Y - cy, origCam.Eye.Z - cz)
vRight.Normalize()
Dim rightEye As Point = tg.CreatePoint(cx + vRight.X * camDist, cy + vRight.Y * camDist, cz + vRight.Z * camDist)
Dim rightUp  As UnitVector = origCam.UpVector

' 4. BACK VIEW TỪ VIEWCUBE (Nhân cự ly camDist)
origCam.ViewOrientationType = ViewOrientationTypeEnum.kBackViewOrientation
origCam.Fit()
origCam.ApplyWithoutTransition()
Dim vBack As Vector = tg.CreateVector(origCam.Eye.X - cx, origCam.Eye.Y - cy, origCam.Eye.Z - cz)
vBack.Normalize()
Dim backEye As Point = tg.CreatePoint(cx + vBack.X * camDist, cy + vBack.Y * camDist, cz + vBack.Z * camDist)
Dim backUp  As UnitVector = origCam.UpVector

' 5. LEFT VIEW TỪ VIEWCUBE (Nhân cự ly camDist)
origCam.ViewOrientationType = ViewOrientationTypeEnum.kLeftViewOrientation
origCam.Fit()
origCam.ApplyWithoutTransition()
Dim vLeft As Vector = tg.CreateVector(origCam.Eye.X - cx, origCam.Eye.Y - cy, origCam.Eye.Z - cz)
vLeft.Normalize()
Dim leftEye As Point = tg.CreatePoint(cx + vLeft.X * camDist, cy + vLeft.Y * camDist, cz + vLeft.Z * camDist)
Dim leftUp  As UnitVector = origCam.UpVector

' 6. BOTTOM VIEW TỪ VIEWCUBE (Nhân cự ly camDist)
origCam.ViewOrientationType = ViewOrientationTypeEnum.kBottomViewOrientation
origCam.Fit()
origCam.ApplyWithoutTransition()
Dim vBottom As Vector = tg.CreateVector(origCam.Eye.X - cx, origCam.Eye.Y - cy, origCam.Eye.Z - cz)
vBottom.Normalize()
Dim bottomEye As Point = tg.CreatePoint(cx + vBottom.X * camDist, cy + vBottom.Y * camDist, cz + vBottom.Z * camDist)
Dim bottomUp  As UnitVector = origCam.UpVector

' Khung nhìn Extents cho 3 mặt chiếu Ortho (Chừa lề cho đường kích thước)
Dim orthoH_Front As Double, orthoW_Front As Double
Dim orthoH_Top   As Double, orthoW_Top   As Double
Dim orthoH_Right As Double, orthoW_Right As Double

If isVertical Then
    orthoW_Front = Math.Max(dx, dy * aspect) / CFG_FitPadding
    orthoH_Front = orthoW_Front / aspect
    
    orthoW_Top   = Math.Max(dx, dz * aspect) / CFG_FitPadding
    orthoH_Top   = orthoW_Top / aspect
    
    orthoW_Right = Math.Max(dz, dy * aspect) / CFG_FitPadding
    orthoH_Right = orthoW_Right / aspect
Else
    ' KHUNG NGANG 16:9: Khóa chặt chiều cao để mô hình to lớn sừng sững chiếm trọn chiều cao
    orthoH_Front = Math.Max(dy, dx / aspect) / CFG_FitPadding
    orthoW_Front = orthoH_Front * aspect
    
    orthoH_Top   = Math.Max(dz, dx / aspect) / CFG_FitPadding
    orthoW_Top   = orthoH_Top * aspect
    
    orthoH_Right = Math.Max(dy, dz / aspect) / CFG_FitPadding
    orthoW_Right = orthoH_Right * aspect
End If

' TÂM QUAY VẬT LÝ CHÍNH XÁC 100% (TRỌNG TÂM HÌNH HỌC DỊCH NHẸ XUỐNG ĐỂ MÔ HÌNH NỔI LÊN TRÊN)
Dim centerPt As Point = tg.CreatePoint(cx, targetY, cz)

' ==============================================================================
' SECTION 3.1: CỰ LY TIÊU CỰ FIT 3D CHỐNG GẦN CHO VẬT DÀI NẰM NGANG & VẬT CAO ĐỨNG
' ==============================================================================
' Đường kính bao trên mặt phẳng đáy XZ khi mô hình xoay tròn 360 độ quanh trục Y
Dim diagXZ As Double = Math.Sqrt(dx * dx + dz * dz)

' Chiều cao và chiều rộng biểu kiến 3D khi nhìn nghiêng ở góc 3/4
Dim apparentH_Bottom As Double = dy * Math.Cos(Math.Abs(elevAngle_Bottom)) + Math.Max(dx, dz) * 0.707 * Math.Sin(Math.Abs(elevAngle_Bottom))
Dim apparentH_Top    As Double = dy * Math.Cos(Math.Abs(elevAngle_Top)) + Math.Max(dx, dz) * 0.707 * Math.Sin(Math.Abs(elevAngle_Top))
Dim apparentW_3D     As Double = (dx + dz) * 0.707 ' Bề rộng thực tế nhìn ở góc 45 độ

' Góc mở nửa của Camera Perspective (PerspectiveAngle = 0.52 rad)
Dim tanHalfFOV_V As Double = Math.Tan(0.52 / 2.0) ' ~0.266
Dim tanHalfFOV_H As Double = tanHalfFOV_V * aspect

Dim heroDist3D_Bottom As Double
Dim heroDist3D_Top    As Double

Dim distV_Bottom As Double = (apparentH_Bottom / targetFillV) / (2.0 * tanHalfFOV_V)
Dim distH_Bottom As Double = (diagXZ / targetFillH) / (2.0 * tanHalfFOV_H)
heroDist3D_Bottom = Math.Max(distV_Bottom, distH_Bottom)

Dim distV_Top As Double = (apparentH_Top / targetFillV) / (2.0 * tanHalfFOV_V)
Dim distH_Top As Double = (diagXZ / targetFillH) / (2.0 * tanHalfFOV_H)
heroDist3D_Top = Math.Max(distV_Top, distH_Top)

' ==============================================================================
' ĐO CỰ LY CAMERA CHUẨN XÁC DỰA VÀO FIT() (LOẠI TRỪ ẢO GIÁC RANGEBOX CỦA INVENTOR)
' ==============================================================================
Try
    Dim oCamTemp As Camera = oApp.ActiveView.Camera
    oCamTemp.Perspective = True
    oCamTemp.PerspectiveAngle = 0.52
    oCamTemp.Target = centerPt
    
    ' Tính toán cho Bottom (Cảnh đầu Scene 1 Intro)
    oCamTemp.Eye = tg.CreatePoint(cx + 100 * Math.Cos(-Math.PI/4.0), targetY + 100 * Math.Sin(elevAngle_Bottom), cz + 100 * Math.Sin(-Math.PI/4.0))
    oCamTemp.UpVector = tg.CreateUnitVector(0, 1, 0)
    oCamTemp.Fit()
    Dim fitDistBottom As Double = oApp.MeasureTools.GetMinimumDistance(oCamTemp.Eye, oCamTemp.Target)
    heroDist3D_Bottom = fitDistBottom * heroDistFactor
    
    ' Tính toán cho Top (Cảnh cuối Scene 5 Outro)
    oCamTemp.Eye = tg.CreatePoint(cx + 100 * Math.Cos(-Math.PI/4.0), targetY + 100 * Math.Sin(elevAngle_Top), cz + 100 * Math.Sin(-Math.PI/4.0))
    oCamTemp.UpVector = tg.CreateUnitVector(0, 1, 0)
    oCamTemp.Fit()
    Dim fitDistTop As Double = oApp.MeasureTools.GetMinimumDistance(oCamTemp.Eye, oCamTemp.Target)
    heroDist3D_Top = fitDistTop * heroDistFactor
Catch : End Try


' 1. Cảnh đầu (3/4 TRÊN KINH ĐIỂN): Bán kính quay và cao độ trục Y
Dim orbitHeightY_Bottom As Double = targetY + heroDist3D_Bottom * Math.Sin(elevAngle_Bottom)
Dim orbitR_XZ_Bottom    As Double = heroDist3D_Bottom * Math.Cos(elevAngle_Bottom)

' 2. Cảnh cuối (3/4 TRÊN): Bán kính quay và cao độ trục Y
Dim orbitHeightY_Top As Double = targetY + heroDist3D_Top * Math.Sin(elevAngle_Top)
Dim orbitR_XZ_Top    As Double = heroDist3D_Top * Math.Cos(elevAngle_Top)

' GÓC QUAY BAN ĐẦU CHUẨN XÁC (ISOMETRIC 45 ĐỘ TRỌNG TÂM)
Dim initialAngle As Double = -Math.PI / 4.0 ' -45 độ chuẩn Isometric Front-Right

' 3. Điểm ViewCube Fit-To-View (Góc 3/4 Trên chuẩn cơ khí, UpVector=(0,1,0) ĐỂ MÔ HÌNH LUÔN ĐỨNG THẲNG 90 ĐỘ)
' (Điểm ViewCube Fit-To-View fitCubeEye / fitCubeTgt / fitCubeUp đã được trích xuất 100% từ ViewCube ở trên)

' Điểm xuất phát Scene 1 (Góc 3/4 Trên - Toàn cảnh hoàn hảo)
Dim introEye As Point = tg.CreatePoint(cx + orbitR_XZ_Bottom * Math.Cos(initialAngle), orbitHeightY_Bottom, cz + orbitR_XZ_Bottom * Math.Sin(initialAngle))

' ==============================================================================
' SECTION 4: THƯ MỤC XUẤT 06_Renders_and_Media
' ==============================================================================
Dim docDir As String = System.IO.Path.GetDirectoryName(oDoc.FullFileName)
Dim projectDir As String = docDir
If docDir.ToLower().EndsWith("\01_assemblies") OrElse docDir.ToLower().EndsWith("\02_parts") OrElse docDir.ToLower().EndsWith("\03_drawings_2d") Then
    projectDir = System.IO.Directory.GetParent(docDir).FullName
End If

Dim mediaDir As String = System.IO.Path.Combine(projectDir, "06_Renders_and_Media")
Dim videoDir As String = System.IO.Path.Combine(mediaDir, "04_Finished_Videos\02_Social_Branded")
Dim snapshotDir As String = System.IO.Path.Combine(mediaDir, "04_Watermarked_Exports")
Dim baseName As String = System.IO.Path.GetFileNameWithoutExtension(oDoc.FullFileName)
Dim frameDir As String = "d:\WT3D_Project\TEMP_FRAMES_" & baseName
If Not System.IO.Directory.Exists(frameDir) Then
    Try : System.IO.Directory.CreateDirectory(frameDir) : Catch : End Try
End If
Try
    For Each oldPng As String In System.IO.Directory.GetFiles(frameDir, "*.png")
        Try : System.IO.File.Delete(oldPng) : Catch : End Try
    Next
Catch : End Try

If Not System.IO.Directory.Exists(videoDir) Then System.IO.Directory.CreateDirectory(videoDir)
If Not System.IO.Directory.Exists(snapshotDir) Then System.IO.Directory.CreateDirectory(snapshotDir)
If Not System.IO.Directory.Exists(frameDir) Then System.IO.Directory.CreateDirectory(frameDir)

' Dọn dẹp rác hiển thị triệt để 100% (Tắt mọi mặt phẳng ở cấp Assembly, Part con và View)
Try
    ' 2. Quét dọn sạch 100% Sketches 2D/3D, Surface Bodies không phải Solid, Work Surfaces, Work Features
    Try : oDoc.ObjectVisibility.Sketches = False : Catch : End Try
    Try : oDoc.ObjectVisibility.Sketches3D = False : Catch : End Try
    Try : oDoc.ObjectVisibility.ConstructionSurfaces = False : Catch : End Try
    Try : oDoc.ObjectVisibility.WorkSurfaces = True : Catch : End Try
    Try : oDoc.ObjectVisibility.AllWorkFeatures = False : Catch : End Try
    Try : oDoc.ObjectVisibility.UserWorkPlanes = False : Catch : End Try
    Try : oDoc.ObjectVisibility.OriginWorkPlanes = False : Catch : End Try
    Try : oDoc.ObjectVisibility.UserWorkAxes = False : Catch : End Try
    Try : oDoc.ObjectVisibility.OriginWorkAxes = False : Catch : End Try
    Try : oDoc.ObjectVisibility.UserWorkPoints = False : Catch : End Try
    Try : oDoc.ObjectVisibility.OriginWorkPoints = False : Catch : End Try
    Try : oDoc.ObjectVisibility.IMateGlyphs = False : Catch : End Try
    Try : oDoc.ObjectVisibility.Joints = False : Catch : End Try

    Try
        For Each rDoc As Document In oDoc.AllReferencedDocuments
            If rDoc.DocumentType = DocumentTypeEnum.kPartDocumentObject Then
                Dim pDef As PartComponentDefinition = CType(rDoc, PartDocument).ComponentDefinition
                For Each sk As PlanarSketch In pDef.Sketches : Try : sk.Visible = False : Catch : End Try : Next
                For Each sk3d As Sketch3D In pDef.Sketches3D : Try : sk3d.Visible = False : Catch : End Try : Next
                For Each wp As WorkPlane In pDef.WorkPlanes : Try : wp.Visible = False : Catch : End Try : Next
                For Each wa As WorkAxis In pDef.WorkAxes : Try : wa.Visible = False : Catch : End Try : Next
                For Each wpnt As WorkPoint In pDef.WorkPoints : Try : wpnt.Visible = False : Catch : End Try : Next
            End If
        Next
    Catch : End Try

    If oDoc.DocumentType = DocumentTypeEnum.kPartDocumentObject Then
        Try
            Dim pDef As PartComponentDefinition = CType(oDoc, PartDocument).ComponentDefinition
            For Each sk As PlanarSketch In pDef.Sketches : Try : sk.Visible = False : Catch : End Try : Next
            For Each sk3d As Sketch3D In pDef.Sketches3D : Try : sk3d.Visible = False : Catch : End Try : Next
            For Each wp As WorkPlane In pDef.WorkPlanes : Try : wp.Visible = False : Catch : End Try : Next
            For Each wa As WorkAxis In pDef.WorkAxes : Try : wa.Visible = False : Catch : End Try : Next
            For Each wpnt As WorkPoint In pDef.WorkPoints : Try : wpnt.Visible = False : Catch : End Try : Next
        Catch : End Try
    End If

    ' ==============================================================================
    ' 3. KHÓA CỨNG: LIGHTING STYLE "TWO LIGHTS" + ALL SHADOWS + HƯỚNG ÁNH SÁNG ABOVE
    ' ==============================================================================
    If useKeyShotLighting Then
        Try
            oApp.SilentOperation = True
            Dim isPartDoc3 As Boolean = (TypeOf oDoc Is PartDocument)
            Dim isAsmDoc3 As Boolean = (TypeOf oDoc Is AssemblyDocument)
            Dim oStyles3 As LightingStyles = Nothing
            If isPartDoc3 Then
                oStyles3 = CType(oDoc, PartDocument).LightingStyles
            ElseIf isAsmDoc3 Then
                oStyles3 = CType(oDoc, AssemblyDocument).LightingStyles
            End If
    
            Dim targetLs3 As LightingStyle = Nothing
            If oStyles3 IsNot Nothing Then
                Try : targetLs3 = oStyles3.Item("Two Lights") : Catch : End Try
                If targetLs3 Is Nothing Then
                    For Each ls As LightingStyle In oStyles3
                        If ls.Name.Equals("Two Lights", StringComparison.OrdinalIgnoreCase) Then
                            targetLs3 = ls : Exit For
                        End If
                    Next
                End If
                If targetLs3 Is Nothing Then
                    For Each ls As LightingStyle In oStyles3
                        If ls.Name.ToLower().Contains("two") OrElse ls.Name.Contains("2") Then
                            targetLs3 = ls : Exit For
                        End If
                    Next
                End If
    
                If targetLs3 IsNot Nothing Then
                    Try
                        If targetLs3.StyleLocation = StyleLocationEnum.kLibraryStyleLocation Then
                            targetLs3.ConvertToLocal()
                        End If
                    Catch : End Try
    
                    If isPartDoc3 Then
                        CType(oDoc, PartDocument).ActiveLightingStyle = targetLs3
                    ElseIf isAsmDoc3 Then
                        CType(oDoc, AssemblyDocument).ActiveLightingStyle = targetLs3
                    End If
                End If
            End If
    
            Dim curStyle3 As LightingStyle = Nothing
            If isPartDoc3 Then
                curStyle3 = CType(oDoc, PartDocument).ActiveLightingStyle
            ElseIf isAsmDoc3 Then
                curStyle3 = CType(oDoc, AssemblyDocument).ActiveLightingStyle
            End If
    
            If curStyle3 IsNot Nothing Then
                Try : curStyle3.ShadowDirection = ShadowDirectionEnum.kAboveShadowDirection : Catch : End Try
                Try : curStyle3.Brightness = 0.83 : Catch : End Try
                Try : curStyle3.Ambience = 0.27 : Catch : End Try
                Try : curStyle3.ShadowDensity = 0.48 : Catch : End Try
                Dim lNum As Integer = 1
                For Each lt As Light In curStyle3.Lights
                    If lNum = 1 Then
                        Try : lt.On = True : Catch : End Try
                        Try : lt.Color = ThisApplication.TransientObjects.CreateColor(255, 255, 255) : Catch : End Try
                        Try : lt.Intensity = 1.0 : Catch : End Try
                        Try : lt.Direction = ThisApplication.TransientGeometry.CreateVector(-0.651641, -0.453990, -0.607665) : Catch : End Try
                    ElseIf lNum = 2 Then
                        Try : lt.On = True : Catch : End Try
                        Try : lt.Color = ThisApplication.TransientObjects.CreateColor(255, 255, 255) : Catch : End Try
                        Try : lt.Intensity = 0.87 : Catch : End Try
                        Try : lt.Direction = ThisApplication.TransientGeometry.CreateVector(-0.598518, 0.104528, -0.794261) : Catch : End Try
                    Else
                        Try : lt.On = False : Catch : End Try
                    End If
                    lNum += 1
                Next
            End If
        Catch
        Finally
            oApp.SilentOperation = False
        End Try
    End If
    
    Try : oView.DisplayMode = DisplayModeEnum.kShadedWithEdgesRendering : Catch : End Try
    
    If useKeyShotLighting Then
        Try : oView.ShowGroundShadows = True : Catch : End Try
        Try : oView.ShowAmbientShadows = True : Catch : End Try
        Try : oView.ShowObjectShadows = True : Catch : End Try
        Try : oView.ShowGroundReflections = True : Catch : End Try
    Else
        Try : oView.ShowGroundShadows = orgGround : Catch : End Try
        Try : oView.ShowAmbientShadows = orgAmbient : Catch : End Try
        Try : oView.ShowObjectShadows = orgObject : Catch : End Try
    End If

    ThisApplication.ColorSchemes.BackgroundType = BackgroundTypeEnum.kGradientBackgroundType
    
    ' BẬT KHỬ RĂNG CƯA TỐI ĐA (MAX ANTI-ALIASING & SMOOTHER QUALITY)
    Try : oApp.DisplayOptions.DisplayQuality = DisplayQualityEnum.kSmootherDisplayQuality : Catch : End Try
    Try : oApp.DisplayOptions.AntiAliasing = True : Catch : End Try
    Try : oApp.DisplayOptions.SmoothLines = True : Catch : End Try
Catch : End Try

Dim fc As Integer = 1
Dim isAborted As Boolean = False

' Lambda lưu frame an toàn 100% (chống lỗi COMException 0x80004005 / buffer lock)
Dim SaveSafeFrame As Action(Of String, Integer, Integer) = Sub(fPath As String, w As Integer, h As Integer)
    For attempt As Integer = 1 To 3
        Try
            oCam.SaveAsBitmap(fPath, w, h)
            Exit Sub
        Catch exCom As Exception
            oApp.UserInterfaceManager.DoEvents()
            System.Threading.Thread.Sleep(15)
            Try : oView.Update() : Catch : End Try
            Try : oCam.ApplyWithoutTransition() : Catch : End Try
        End Try
    Next
    Try : oView.SaveAsBitmap(fPath, w, h) : Catch : End Try
End Sub

oApp.StatusBarText = "🎬 WT3D Studio: Đang render [" & modeTag & " " & qualityTag & "]... [GIỮ PHÍM ESC ĐỂ DỪNG]"

' ==============================================================================
' SCENE 1: 3D HERO INTRO (XOAY TRÒN 360 ĐỘ GÓC 3/4 TRÊN KINH ĐIỂN)
' ==============================================================================
Try
    oView.DisplayMode = DisplayModeEnum.kShadedWithEdgesRendering
    oView.ShowAmbientShadows = True
    oView.ShowObjectShadows  = True
    oView.ShowGroundShadows  = True
    oView.ShowGroundReflections = True
    oView.Update()
Catch : End Try

oCam.Perspective = True
oCam.PerspectiveAngle = 0.52
oCam.Apply()

For i As Integer = 1 To fIntro
    oApp.UserInterfaceManager.DoEvents()
    If CheckEscapeKey() Then : isAborted = True : GoTo AbortRender : End If
    
    Dim t As Double = CDbl(i) / CDbl(fIntro)
    Dim curAng As Double = initialAngle + (Math.PI * 2.0) * t
    
    Dim eyeX As Double = cx + orbitR_XZ_Bottom * Math.Cos(curAng)
    Dim eyeY As Double = orbitHeightY_Bottom
    Dim eyeZ As Double = cz + orbitR_XZ_Bottom * Math.Sin(curAng)
    
    oCam.Eye = tg.CreatePoint(eyeX, eyeY, eyeZ)
    oCam.Target = centerPt
    oCam.UpVector = tg.CreateUnitVector(0, 1, 0)
    oCam.Perspective = True
    oCam.PerspectiveAngle = 0.52
    oCam.ApplyWithoutTransition()
    SaveSafeFrame(frameDir & "\FRAME_" & fc.ToString("00000") & ".png", CFG_RenderW, CFG_RenderH) : fc += 1
Next

' ==============================================================================
' FLIGHT 1: GÓC 3/4 TRÊN -> FRONT VIEW (SPEED RAMP WHIP PAN)
' ==============================================================================
Dim curEyeX As Double = introEye.X, curEyeY As Double = introEye.Y, curEyeZ As Double = introEye.Z
For i As Integer = 1 To fFlight
    oApp.UserInterfaceManager.DoEvents()
    If CheckEscapeKey() Then : isAborted = True : GoTo AbortRender : End If
    
    Dim t As Double = CDbl(i) / CDbl(fFlight)
    Dim e As Double = (Math.Tanh(2.8 * (2.0 * t - 1.0)) / Math.Tanh(2.8) + 1.0) / 2.0
    
    oCam.Eye = tg.CreatePoint(curEyeX + (frontEye.X - curEyeX) * e, curEyeY + (frontEye.Y - curEyeY) * e, curEyeZ + (frontEye.Z - curEyeZ) * e)
    oCam.Target = tg.CreatePoint(cx, cy, cz)
    oCam.UpVector = frontUp
    oCam.Perspective = True
    oCam.PerspectiveAngle = 0.52
    oCam.ApplyWithoutTransition()
    SaveSafeFrame(frameDir & "\FRAME_" & fc.ToString("00000") & ".png", CFG_RenderW, CFG_RenderH) : fc += 1
Next

' ==============================================================================
' SCENE 2: FRONT VIEW HOLD (MODE PURE ORTHO + KHUNG DÂY NÉT THẤY + TẮT HẾT SHADOW)
' ==============================================================================
Try
    oView.ShowAmbientShadows = False
    oView.ShowObjectShadows  = False
    oView.ShowGroundShadows  = False
    oView.ShowGroundReflections = True
    oView.DisplayMode = DisplayModeEnum.kWireframeNoHiddenEdges
    oView.Update()
Catch : End Try

oCam.ViewOrientationType = ViewOrientationTypeEnum.kFrontViewOrientation
oCam.Perspective = False
oCam.Fit()
Dim curExtW_F As Double = 0, curExtH_F As Double = 0
oCam.GetExtents(curExtW_F, curExtH_F)
oCam.SetExtents(curExtW_F * 1.35, curExtH_F * 1.35)
oCam.ApplyWithoutTransition() : oApp.UserInterfaceManager.DoEvents()

oApp.StatusBarText = "📐 FRONT VIEW: Pure Ortho + Nét Xanh Dương + Kích Thước [ESC để dừng]"

' Snapshot 5: Front Ortho Blueprint with Dimensions
Dim snapFront As String = System.IO.Path.Combine(snapshotDir, baseName & "_05_Blueprint_Front_Elevation_Dim.png")
Try : SaveSafeFrame(snapFront, CFG_RenderW, CFG_RenderH) : Catch : End Try

Dim frontStartFrame As Integer = fc
For i As Integer = 1 To fHold
    oApp.UserInterfaceManager.DoEvents()
    If CheckEscapeKey() Then : isAborted = True : GoTo AbortRender : End If
    Dim curFramePath As String = frameDir & "\FRAME_" & fc.ToString("00000") & ".png"
    SaveSafeFrame(curFramePath, CFG_RenderW, CFG_RenderH) : fc += 1
Next
Dim frontEndFrame As Integer = fc - 1

' ==============================================================================
' FLIGHT 2: FRONT VIEW -> TOP VIEW (SPEED RAMP WHIP PAN)
' ==============================================================================
Try
    oView.DisplayMode = DisplayModeEnum.kShadedWithEdgesRendering
    oView.ShowAmbientShadows = True
    oView.ShowObjectShadows  = True
    oView.ShowGroundShadows  = True
    oView.Update()
Catch : End Try

oCam.Perspective = True
oCam.PerspectiveAngle = 0.52

curEyeX = frontEye.X : curEyeY = frontEye.Y : curEyeZ = frontEye.Z
For i As Integer = 1 To fFlight
    oApp.UserInterfaceManager.DoEvents()
    If CheckEscapeKey() Then : isAborted = True : GoTo AbortRender : End If
    
    Dim t As Double = CDbl(i) / CDbl(fFlight)
    Dim e As Double = (Math.Tanh(2.8 * (2.0 * t - 1.0)) / Math.Tanh(2.8) + 1.0) / 2.0
    Dim arcZ As Double = cz + camDist * 0.3 * Math.Sin(Math.PI * t)
    
    Dim upX As Double = frontUp.X + (topUp.X - frontUp.X) * e
    Dim upY As Double = frontUp.Y + (topUp.Y - frontUp.Y) * e
    Dim upZ As Double = frontUp.Z + (topUp.Z - frontUp.Z) * e
    
    oCam.Eye = tg.CreatePoint(curEyeX + (topEye.X - curEyeX) * e, curEyeY + (topEye.Y - curEyeY) * e, curEyeZ + (topEye.Z - curEyeZ) * e + arcZ * 0.2)
    oCam.Target = tg.CreatePoint(cx, cy, cz)
    oCam.UpVector = tg.CreateUnitVector(upX, upY, upZ)
    oCam.Perspective = True
    oCam.PerspectiveAngle = 0.52
    oCam.ApplyWithoutTransition()
    SaveSafeFrame(frameDir & "\FRAME_" & fc.ToString("00000") & ".png", CFG_RenderW, CFG_RenderH) : fc += 1
Next

' ==============================================================================
' SCENE 3: TOP VIEW HOLD (MODE PURE ORTHO + KHUNG DÂY NÉT THẤY + TẮT HẾT SHADOW)
' ==============================================================================
Try
    oView.ShowAmbientShadows = False
    oView.ShowObjectShadows  = False
    oView.ShowGroundShadows  = False
    oView.ShowGroundReflections = True
    oView.DisplayMode = DisplayModeEnum.kWireframeNoHiddenEdges
    oView.Update()
Catch : End Try

oCam.ViewOrientationType = ViewOrientationTypeEnum.kTopViewOrientation
oCam.Perspective = False
oCam.Fit()
Dim curExtW_T As Double = 0, curExtH_T As Double = 0
oCam.GetExtents(curExtW_T, curExtH_T)
oCam.SetExtents(curExtW_T * 1.35, curExtH_T * 1.35)
oCam.ApplyWithoutTransition() : oApp.UserInterfaceManager.DoEvents()

oApp.StatusBarText = "📐 TOP VIEW: Pure Ortho + Nét Xanh Dương + Kích Thước [ESC để dừng]"

' Snapshot 6: Top Ortho Blueprint with Dimensions
Dim snapTop As String = System.IO.Path.Combine(snapshotDir, baseName & "_06_Blueprint_Top_Plan_Dim.png")
Try : SaveSafeFrame(snapTop, CFG_RenderW, CFG_RenderH) : Catch : End Try

Dim topStartFrame As Integer = fc
For i As Integer = 1 To fHold
    oApp.UserInterfaceManager.DoEvents()
    If CheckEscapeKey() Then : isAborted = True : GoTo AbortRender : End If
    Dim curFramePath As String = frameDir & "\FRAME_" & fc.ToString("00000") & ".png"
    SaveSafeFrame(curFramePath, CFG_RenderW, CFG_RenderH) : fc += 1
Next
Dim topEndFrame As Integer = fc - 1

' ==============================================================================
' FLIGHT 3: TOP VIEW -> LEFT VIEW (SPEED RAMP WHIP PAN)
' ==============================================================================
Try
    oView.DisplayMode = DisplayModeEnum.kShadedWithEdgesRendering
    oView.ShowAmbientShadows = True
    oView.ShowObjectShadows  = True
    oView.ShowGroundShadows  = True
    oView.Update()
Catch : End Try

oCam.Perspective = True
oCam.PerspectiveAngle = 0.52

curEyeX = topEye.X : curEyeY = topEye.Y : curEyeZ = topEye.Z
For i As Integer = 1 To fFlight
    oApp.UserInterfaceManager.DoEvents()
    If CheckEscapeKey() Then : isAborted = True : GoTo AbortRender : End If
    
    Dim t As Double = CDbl(i) / CDbl(fFlight)
    Dim e As Double = (Math.Tanh(2.8 * (2.0 * t - 1.0)) / Math.Tanh(2.8) + 1.0) / 2.0
    
    Dim upX As Double = topUp.X + (leftUp.X - topUp.X) * e
    Dim upY As Double = topUp.Y + (leftUp.Y - topUp.Y) * e
    Dim upZ As Double = topUp.Z + (leftUp.Z - topUp.Z) * e
    
    oCam.Eye = tg.CreatePoint(curEyeX + (leftEye.X - curEyeX) * e, curEyeY + (leftEye.Y - curEyeY) * e, curEyeZ + (leftEye.Z - curEyeZ) * e)
    oCam.Target = tg.CreatePoint(cx, cy, cz)
    oCam.UpVector = tg.CreateUnitVector(upX, upY, upZ)
    oCam.Perspective = True
    oCam.PerspectiveAngle = 0.52
    oCam.ApplyWithoutTransition()
    
    SaveSafeFrame(frameDir & "\FRAME_" & fc.ToString("00000") & ".png", CFG_RenderW, CFG_RenderH) : fc += 1
Next

' ==============================================================================
' SCENE 4: LEFT VIEW HOLD (MODE PURE ORTHO + KHUNG DÂY NÉT THẤY + TẮT HẾT SHADOW)
' ==============================================================================
Try
    oView.ShowAmbientShadows = False
    oView.ShowObjectShadows  = False
    oView.ShowGroundShadows  = False
    oView.ShowGroundReflections = True
    oView.DisplayMode = DisplayModeEnum.kWireframeNoHiddenEdges
    oView.Update()
Catch : End Try

oCam.ViewOrientationType = ViewOrientationTypeEnum.kLeftViewOrientation
oCam.Perspective = False
oCam.Fit()
Dim curExtW_L As Double = 0, curExtH_L As Double = 0
oCam.GetExtents(curExtW_L, curExtH_L)
oCam.SetExtents(curExtW_L * 1.35, curExtH_L * 1.35)
oCam.ApplyWithoutTransition() : oApp.UserInterfaceManager.DoEvents()

oApp.StatusBarText = "📐 LEFT VIEW: Pure Ortho + Nét Xanh Dương + Kích Thước [ESC để dừng]"

' Snapshot 7: Left Ortho Blueprint with Dimensions
Dim snapLeft As String = System.IO.Path.Combine(snapshotDir, baseName & "_07_Blueprint_Left_Side_Dim.png")
Try : SaveSafeFrame(snapLeft, CFG_RenderW, CFG_RenderH) : Catch : End Try

Dim rightStartFrame As Integer = fc
For i As Integer = 1 To fHold
    oApp.UserInterfaceManager.DoEvents()
    If CheckEscapeKey() Then : isAborted = True : GoTo AbortRender : End If
    Dim curFramePath As String = frameDir & "\FRAME_" & fc.ToString("00000") & ".png"
    SaveSafeFrame(curFramePath, CFG_RenderW, CFG_RenderH) : fc += 1
Next
Dim rightEndFrame As Integer = fc - 1

' ==============================================================================
' FLIGHT 4: RIGHT VIEW -> GÓC 3/4 TRÊN (SPEED RAMP WHIP PAN)
' ==============================================================================
Try
    oView.DisplayMode = DisplayModeEnum.kShadedWithEdgesRendering
    oView.ShowAmbientShadows = True
    oView.ShowObjectShadows  = True
    oView.ShowGroundShadows  = True
    oView.Update()
Catch : End Try

oCam.Perspective = True
oCam.PerspectiveAngle = 0.52

' Điểm bắt đầu xoay góc 3/4 trên
Dim outroStartAngle As Double = initialAngle + Math.PI * 0.4
Dim outroStartEye As Point = tg.CreatePoint(cx + orbitR_XZ_Top * Math.Cos(outroStartAngle), orbitHeightY_Top, cz + orbitR_XZ_Top * Math.Sin(outroStartAngle))

curEyeX = leftEye.X : curEyeY = leftEye.Y : curEyeZ = leftEye.Z
For i As Integer = 1 To fFlight
    oApp.UserInterfaceManager.DoEvents()
    If CheckEscapeKey() Then : isAborted = True : GoTo AbortRender : End If
    
    Dim t As Double = CDbl(i) / CDbl(fFlight)
    Dim e As Double = (Math.Tanh(2.8 * (2.0 * t - 1.0)) / Math.Tanh(2.8) + 1.0) / 2.0
    
    oCam.Eye = tg.CreatePoint(curEyeX + (outroStartEye.X - curEyeX) * e, curEyeY + (outroStartEye.Y - curEyeY) * e, curEyeZ + (outroStartEye.Z - curEyeZ) * e)
    oCam.Target = centerPt
    oCam.UpVector = tg.CreateUnitVector(0, 1, 0)
    oCam.Perspective = True
    oCam.PerspectiveAngle = 0.52
    oCam.ApplyWithoutTransition()
    
    SaveSafeFrame(frameDir & "\FRAME_" & fc.ToString("00000") & ".png", CFG_RenderW, CFG_RenderH) : fc += 1
Next

' ==============================================================================
' SCENE 5: CẢNH CUỐI XOAY 3/4 TRÊN (CONSTANT ANGULAR VELOCITY - SIÊU MƯỢT MÀ)
' ==============================================================================
oCam.Perspective = True
oCam.PerspectiveAngle = 0.52
oApp.StatusBarText = "🌟 SCENE 5: Xoay 3/4 Trên [ESC để dừng]"

Dim outroEndEye As Point = outroStartEye
For i As Integer = 1 To fOutro
    oApp.UserInterfaceManager.DoEvents()
    If CheckEscapeKey() Then : isAborted = True : GoTo AbortRender : End If
    
    Dim t As Double = CDbl(i) / CDbl(fOutro)
    Dim curAng As Double = outroStartAngle + (Math.PI * 1.2) * t
    
    Dim eyeX As Double = cx + orbitR_XZ_Top * Math.Cos(curAng)
    Dim eyeY As Double = orbitHeightY_Top
    Dim eyeZ As Double = cz + orbitR_XZ_Top * Math.Sin(curAng)
    
    outroEndEye = tg.CreatePoint(eyeX, eyeY, eyeZ)
    oCam.Eye = outroEndEye
    oCam.Target = centerPt
    oCam.UpVector = tg.CreateUnitVector(0, 1, 0)
    oCam.Perspective = True
    oCam.PerspectiveAngle = 0.52
    oCam.ApplyWithoutTransition()
    
    SaveSafeFrame(frameDir & "\FRAME_" & fc.ToString("00000") & ".png", CFG_RenderW, CFG_RenderH) : fc += 1
Next

' ==============================================================================
' SCENE 6: CHỐT CẢNH FIT TO VIEW CHUẨN CỦA VIEWCUBE (ISOMETRIC TOP RIGHT)
' ==============================================================================
oApp.StatusBarText = "🏁 SCENE 6: Chốt cảnh Fit To View của Cube [ESC để dừng]"

' Chuyến bay nhẹ đáp về góc ViewCube Fit To View kinh điển
curEyeX = outroEndEye.X : curEyeY = outroEndEye.Y : curEyeZ = outroEndEye.Z
Dim curTgtX As Double = oCam.Target.X, curTgtY As Double = oCam.Target.Y, curTgtZ As Double = oCam.Target.Z
Dim curUpX  As Double = oCam.UpVector.X, curUpY  As Double = oCam.UpVector.Y, curUpZ  As Double = oCam.UpVector.Z

For i As Integer = 1 To fFlight
    oApp.UserInterfaceManager.DoEvents()
    If CheckEscapeKey() Then : isAborted = True : GoTo AbortRender : End If
    
    Dim t As Double = CDbl(i) / CDbl(fFlight)
    Dim e As Double = (Math.Tanh(2.8 * (2.0 * t - 1.0)) / Math.Tanh(2.8) + 1.0) / 2.0
    
    oCam.Eye = tg.CreatePoint(curEyeX + (fitCubeEye.X - curEyeX) * e, curEyeY + (fitCubeEye.Y - curEyeY) * e, curEyeZ + (fitCubeEye.Z - curEyeZ) * e)
    oCam.Target = tg.CreatePoint(curTgtX + (fitCubeTgt.X - curTgtX) * e, curTgtY + (fitCubeTgt.Y - curTgtY) * e, curTgtZ + (fitCubeTgt.Z - curTgtZ) * e)
    oCam.UpVector = tg.CreateUnitVector(curUpX + (fitCubeUp.X - curUpX) * e, curUpY + (fitCubeUp.Y - curUpY) * e, curUpZ + (fitCubeUp.Z - curUpZ) * e)
    oCam.Perspective = True
    oCam.PerspectiveAngle = 0.52
    oCam.ApplyWithoutTransition()
    
    SaveSafeFrame(frameDir & "\FRAME_" & fc.ToString("00000") & ".png", CFG_RenderW, CFG_RenderH) : fc += 1
Next

' Giữ cố định (Hold) tại góc Fit To View của ViewCube (Đã phóng to cận cảnh siêu nét 98%)
oCam.Eye = fitCubeEye
oCam.Target = fitCubeTgt
oCam.UpVector = fitCubeUp
oCam.Perspective = True
oCam.PerspectiveAngle = 0.52
oCam.ApplyWithoutTransition() : oApp.UserInterfaceManager.DoEvents()

For i As Integer = 1 To fFinale
    oApp.UserInterfaceManager.DoEvents()
    If CheckEscapeKey() Then : isAborted = True : GoTo AbortRender : End If
    SaveSafeFrame(frameDir & "\FRAME_" & fc.ToString("00000") & ".png", CFG_RenderW, CFG_RenderH) : fc += 1
Next

' ==============================================================================
' MASTER 3D MARKETPLACE SNAPSHOT SUITE (BỘ 19 ẢNH XUẤT BẢN CHUẨN SÀN 3D QUỐC TẾ)
' Tối ưu: Gom nhóm theo DisplayMode → Giảm chuyển đổi GPU → Mượt mà tối đa
' ==============================================================================
oApp.StatusBarText = "📸 Đang xuất trọn bộ 19 ảnh Marketplace (Hero, Studio, Wireframe, Clay)..."

' Helper: Chỉ GC khi độ phân giải cao (2K trở lên) để tránh tràn VRAM
Dim needGC As Boolean = (is4K OrElse is2K)
Dim gcDelay As Integer = If(is4K, 500, 200) ' 4K cần nghỉ lâu hơn 2K

' UpVector chuẩn dùng lại nhiều lần
Dim stdUpY As UnitVector = tg.CreateUnitVector(0, 1, 0)

' ──────────────────────────────────────────────────────────────────────────────
' NHÓM A: TẤT CẢ ẢNH SHADED WITH EDGES (1 lần GC duy nhất trước nhóm)
' ──────────────────────────────────────────────────────────────────────────────
oView.DisplayMode = DisplayModeEnum.kShadedWithEdgesRendering
oView.ShowAmbientShadows = True : oView.ShowObjectShadows = True : oView.ShowGroundShadows = True
oView.Update()
' ✅ PERF: GC 1 lần trước cả nhóm A (11 ảnh) thay vì gọi lặp lại mỗi ảnh
If needGC Then : System.GC.Collect() : System.GC.WaitForPendingFinalizers() : System.Threading.Thread.Sleep(gcDelay) : oApp.UserInterfaceManager.DoEvents() : End If

' A1. Hero Iso Top Right (ViewCube Fit To View Phóng To Cận Cảnh - Thumbnail Video FRAME_00000)
Try
    oCam.Eye = fitCubeEye : oCam.Target = fitCubeTgt : oCam.UpVector = fitCubeUp
    oCam.Perspective = True : oCam.PerspectiveAngle = 0.52
    oCam.ApplyWithoutTransition() : oApp.UserInterfaceManager.DoEvents()
    SaveSafeFrame(System.IO.Path.Combine(snapshotDir, baseName & "_01_Hero3D_Iso_TopRight.png"), CFG_RenderW, CFG_RenderH)
    Try : SaveSafeFrame(frameDir & "\FRAME_00000.png", CFG_RenderW, CFG_RenderH) : Catch : End Try
Catch : End Try

' A2. Hero Iso Top Left
Try
    Dim isoLeftEye As Point = tg.CreatePoint(cx - orbitR_XZ_Top * Math.Cos(Math.Abs(initialAngle)), orbitHeightY_Top, cz - orbitR_XZ_Top * Math.Sin(Math.Abs(initialAngle)))
    oCam.Eye = isoLeftEye : oCam.Target = centerPt : oCam.UpVector = stdUpY
    oCam.Perspective = True : oCam.PerspectiveAngle = 0.52
    oCam.ApplyWithoutTransition() : oApp.UserInterfaceManager.DoEvents()
    SaveSafeFrame(System.IO.Path.Combine(snapshotDir, baseName & "_02_Hero3D_Iso_TopLeft.png"), CFG_RenderW, CFG_RenderH)
Catch : End Try

' A3. Hero Low Angle (3/4 Dưới)
Try
    oCam.Eye = introEye : oCam.Target = centerPt : oCam.UpVector = stdUpY
    oCam.Perspective = True : oCam.PerspectiveAngle = 0.52
    oCam.ApplyWithoutTransition() : oApp.UserInterfaceManager.DoEvents()
    SaveSafeFrame(System.IO.Path.Combine(snapshotDir, baseName & "_03_Hero3D_LowAngle.png"), CFG_RenderW, CFG_RenderH)
Catch : End Try

' A4. Hero Iso Back Right (+90°)
Try
    Dim isoBackRightEye As Point = tg.CreatePoint(cx + orbitR_XZ_Top * Math.Cos(initialAngle + Math.PI / 2.0), orbitHeightY_Top, cz + orbitR_XZ_Top * Math.Sin(initialAngle + Math.PI / 2.0))
    oCam.Eye = isoBackRightEye : oCam.Target = centerPt : oCam.UpVector = stdUpY
    oCam.Perspective = True : oCam.PerspectiveAngle = 0.52
    oCam.ApplyWithoutTransition() : oApp.UserInterfaceManager.DoEvents()
    SaveSafeFrame(System.IO.Path.Combine(snapshotDir, baseName & "_11_Hero3D_Iso_BackRight.png"), CFG_RenderW, CFG_RenderH)
Catch : End Try

' A5. Hero Iso Back Left (+180°)
Try
    Dim isoBackLeftEye As Point = tg.CreatePoint(cx + orbitR_XZ_Top * Math.Cos(initialAngle + Math.PI), orbitHeightY_Top, cz + orbitR_XZ_Top * Math.Sin(initialAngle + Math.PI))
    oCam.Eye = isoBackLeftEye : oCam.Target = centerPt : oCam.UpVector = stdUpY
    oCam.Perspective = True : oCam.PerspectiveAngle = 0.52
    oCam.ApplyWithoutTransition() : oApp.UserInterfaceManager.DoEvents()
    SaveSafeFrame(System.IO.Path.Combine(snapshotDir, baseName & "_12_Hero3D_Iso_BackLeft.png"), CFG_RenderW, CFG_RenderH)
Catch : End Try

' A6. Studio Clean Front (Ortho 2D - Safe Area chống chạm Icon phải)
Try
    oCam.ViewOrientationType = ViewOrientationTypeEnum.kFrontViewOrientation
    oCam.Perspective = False
    oCam.Fit()
    Dim extW_08 As Double = 0, extH_08 As Double = 0
    oCam.GetExtents(extW_08, extH_08)
    oCam.SetExtents(extW_08 * 1.28, extH_08 * 1.28)
    oCam.ApplyWithoutTransition() : oApp.UserInterfaceManager.DoEvents()
    SaveSafeFrame(System.IO.Path.Combine(snapshotDir, baseName & "_08_Studio_Clean_Front_Shaded.png"), CFG_RenderW, CFG_RenderH)
Catch : End Try

' A7. Studio Clean Top (Ortho 2D - Safe Area)
Try
    oCam.ViewOrientationType = ViewOrientationTypeEnum.kTopViewOrientation
    oCam.Perspective = False
    oCam.Fit()
    Dim extW_09 As Double = 0, extH_09 As Double = 0
    oCam.GetExtents(extW_09, extH_09)
    oCam.SetExtents(extW_09 * 1.28, extH_09 * 1.28)
    oCam.ApplyWithoutTransition() : oApp.UserInterfaceManager.DoEvents()
    SaveSafeFrame(System.IO.Path.Combine(snapshotDir, baseName & "_09_Studio_Clean_Top_Shaded.png"), CFG_RenderW, CFG_RenderH)
Catch : End Try

' A8. Studio Clean Left (Ortho 2D - Safe Area)
Try
    oCam.ViewOrientationType = ViewOrientationTypeEnum.kLeftViewOrientation
    oCam.Perspective = False
    oCam.Fit()
    Dim extW_10 As Double = 0, extH_10 As Double = 0
    oCam.GetExtents(extW_10, extH_10)
    oCam.SetExtents(extW_10 * 1.28, extH_10 * 1.28)
    oCam.ApplyWithoutTransition() : oApp.UserInterfaceManager.DoEvents()
    SaveSafeFrame(System.IO.Path.Combine(snapshotDir, baseName & "_10_Studio_Clean_Left_Shaded.png"), CFG_RenderW, CFG_RenderH)
Catch : End Try

' A9. Studio Clean Back (Ortho 2D - Safe Area)
Try
    oCam.ViewOrientationType = ViewOrientationTypeEnum.kBackViewOrientation
    oCam.Perspective = False
    oCam.Fit()
    Dim extW_13 As Double = 0, extH_13 As Double = 0
    oCam.GetExtents(extW_13, extH_13)
    oCam.SetExtents(extW_13 * 1.28, extH_13 * 1.28)
    oCam.ApplyWithoutTransition() : oApp.UserInterfaceManager.DoEvents()
    SaveSafeFrame(System.IO.Path.Combine(snapshotDir, baseName & "_13_Studio_Clean_Back_Shaded.png"), CFG_RenderW, CFG_RenderH)
Catch : End Try

' A10. Studio Clean Right (Ortho 2D - Safe Area)
Try
    oCam.ViewOrientationType = ViewOrientationTypeEnum.kRightViewOrientation
    oCam.Perspective = False
    oCam.Fit()
    Dim extW_14 As Double = 0, extH_14 As Double = 0
    oCam.GetExtents(extW_14, extH_14)
    oCam.SetExtents(extW_14 * 1.28, extH_14 * 1.28)
    oCam.ApplyWithoutTransition() : oApp.UserInterfaceManager.DoEvents()
    SaveSafeFrame(System.IO.Path.Combine(snapshotDir, baseName & "_14_Studio_Clean_Right_Shaded.png"), CFG_RenderW, CFG_RenderH)
Catch : End Try

' A11. Studio Clean Bottom (Ortho 2D - Safe Area)
Try
    oCam.ViewOrientationType = ViewOrientationTypeEnum.kBottomViewOrientation
    oCam.Perspective = False
    oCam.Fit()
    Dim extW_15 As Double = 0, extH_15 As Double = 0
    oCam.GetExtents(extW_15, extH_15)
    oCam.SetExtents(extW_15 * 1.28, extH_15 * 1.28)
    oCam.ApplyWithoutTransition() : oApp.UserInterfaceManager.DoEvents()
    SaveSafeFrame(System.IO.Path.Combine(snapshotDir, baseName & "_15_Studio_Clean_Bottom_Shaded.png"), CFG_RenderW, CFG_RenderH)
Catch : End Try

' ──────────────────────────────────────────────────────────────────────────────
' NHÓM B: TẤT CẢ ẢNH WIREFRAME (1 lần GC duy nhất trước nhóm)
' ──────────────────────────────────────────────────────────────────────────────
oView.DisplayMode = DisplayModeEnum.kWireframeNoHiddenEdges
oView.ShowAmbientShadows = False : oView.ShowObjectShadows = False : oView.ShowGroundShadows = False
oView.Update()
' ✅ PERF: GC 1 lần trước cả nhóm B (3 ảnh)
If needGC Then : System.GC.Collect() : System.GC.WaitForPendingFinalizers() : System.Threading.Thread.Sleep(gcDelay) : oApp.UserInterfaceManager.DoEvents() : End If

' B1. Wireframe 3D Topology (Perspective - CheckMate)
Try
    oCam.Eye = fitCubeEye : oCam.Target = fitCubeTgt : oCam.UpVector = fitCubeUp
    oCam.Perspective = True : oCam.PerspectiveAngle = 0.52
    oCam.ApplyWithoutTransition() : oApp.UserInterfaceManager.DoEvents()
    SaveSafeFrame(System.IO.Path.Combine(snapshotDir, baseName & "_04_Wireframe3D_Topology_CheckMate.png"), CFG_RenderW, CFG_RenderH)
Catch : End Try

' B2. Wireframe Clean Front (Ortho - Auto-Fit Safe Area)
Try
    oCam.ViewOrientationType = ViewOrientationTypeEnum.kFrontViewOrientation
    oCam.Perspective = False
    oCam.Fit()
    Dim extW_16 As Double = 0, extH_16 As Double = 0
    oCam.GetExtents(extW_16, extH_16)
    oCam.SetExtents(extW_16 * 1.28, extH_16 * 1.28)
    oCam.ApplyWithoutTransition() : oApp.UserInterfaceManager.DoEvents()
    SaveSafeFrame(System.IO.Path.Combine(snapshotDir, baseName & "_16_Wireframe_Clean_Front.png"), CFG_RenderW, CFG_RenderH)
Catch : End Try

' B3. Wireframe Clean Top (Ortho - Auto-Fit Safe Area)
Try
    oCam.ViewOrientationType = ViewOrientationTypeEnum.kTopViewOrientation
    oCam.Perspective = False
    oCam.Fit()
    Dim extW_17 As Double = 0, extH_17 As Double = 0
    oCam.GetExtents(extW_17, extH_17)
    oCam.SetExtents(extW_17 * 1.28, extH_17 * 1.28)
    oCam.ApplyWithoutTransition() : oApp.UserInterfaceManager.DoEvents()
    SaveSafeFrame(System.IO.Path.Combine(snapshotDir, baseName & "_17_Wireframe_Clean_Top.png"), CFG_RenderW, CFG_RenderH)
Catch : End Try

' ──────────────────────────────────────────────────────────────────────────────
' NHÓM C: TẤT CẢ ẢNH MONOCHROME CLAY (1 lần GC duy nhất trước nhóm)
' ──────────────────────────────────────────────────────────────────────────────
oView.DisplayMode = DisplayModeEnum.kMonochromeRendering
oView.ShowAmbientShadows = True : oView.ShowObjectShadows = True : oView.ShowGroundShadows = True
oView.Update()
' ✅ PERF: GC 1 lần trước cả nhóm C (2 ảnh)
If needGC Then : System.GC.Collect() : System.GC.WaitForPendingFinalizers() : System.Threading.Thread.Sleep(gcDelay) : oApp.UserInterfaceManager.DoEvents() : End If

' C1. Clay Hero 3D (Iso Top Right)
Try
    oCam.Eye = fitCubeEye : oCam.Target = fitCubeTgt : oCam.UpVector = fitCubeUp
    oCam.Perspective = True : oCam.PerspectiveAngle = 0.52
    oCam.ApplyWithoutTransition() : oApp.UserInterfaceManager.DoEvents()
    SaveSafeFrame(System.IO.Path.Combine(snapshotDir, baseName & "_18_Monochrome_Clay_Hero3D.png"), CFG_RenderW, CFG_RenderH)
Catch : End Try

' C2. Clay Front (Ortho - Auto-Fit Safe Area)
Try
    oCam.ViewOrientationType = ViewOrientationTypeEnum.kFrontViewOrientation
    oCam.Perspective = False
    oCam.Fit()
    Dim extW_19 As Double = 0, extH_19 As Double = 0
    oCam.GetExtents(extW_19, extH_19)
    oCam.SetExtents(extW_19 * 1.28, extH_19 * 1.28)
    oCam.ApplyWithoutTransition() : oApp.UserInterfaceManager.DoEvents()
    SaveSafeFrame(System.IO.Path.Combine(snapshotDir, baseName & "_19_Monochrome_Clay_Front.png"), CFG_RenderW, CFG_RenderH)
Catch : End Try

    ' ──────────────────────────────────────────────────────────────────────────────
    ' NHÓM D: TỰ ĐỘNG CHỤP ẢNH PHÂN RÃ LINH KIỆN (NẾU PHÁT HIỆN FILE .IPN CÙNG TÊN)
    ' ──────────────────────────────────────────────────────────────────────────────
    Try
        Dim ipnFile As String = System.IO.Path.Combine(docDir, baseName & ".ipn")
        If System.IO.File.Exists(ipnFile) Then
            oApp.StatusBarText = "💥 Phát hiện File Phân Rã (.ipn) -> Đang tự động chụp Exploded View..."
            Dim ipnDoc As Inventor.Document = Nothing
            Dim ipnAlreadyOpen As Boolean = False
            For Each d As Document In oApp.Documents
                If d.FullFileName.ToLower() = ipnFile.ToLower() Then
                    ipnDoc = d : ipnAlreadyOpen = True : Exit For
                End If
            Next
            If ipnDoc Is Nothing Then
                ipnDoc = oApp.Documents.Open(ipnFile, True)
            End If
            If ipnDoc IsNot Nothing Then
                ipnDoc.Activate()
                Dim ipnView As Inventor.View = oApp.ActiveView
                Dim ipnCam As Inventor.Camera = ipnView.Camera
                Try
                    ipnDoc.ObjectVisibility.AllWorkFeatures = False
                    ipnDoc.ObjectVisibility.UserWorkPlanes = False
                    ipnDoc.ObjectVisibility.OriginWorkPlanes = False
                    ipnDoc.ObjectVisibility.Sketches = False
                Catch : End Try
                ipnView.DisplayMode = DisplayModeEnum.kShadedWithEdgesRendering
                ipnView.ShowAmbientShadows = True : ipnView.ShowObjectShadows = True : ipnView.ShowGroundShadows = True
                ipnView.Update()
                ipnCam.Perspective = True : ipnCam.PerspectiveAngle = 0.52
                ipnCam.Fit() : ipnCam.ApplyWithoutTransition()
                Dim cW As Double, cH As Double
                ipnCam.GetExtents(cW, cH)
                ipnCam.SetExtents(cW * 0.72, cH * 0.72)
                ipnCam.ApplyWithoutTransition() : oApp.UserInterfaceManager.DoEvents()
                Dim snapExploded As String = System.IO.Path.Combine(snapshotDir, baseName & "_20_Exploded_BOM_Assembly.png")
                ipnCam.SaveAsBitmap(snapExploded, CFG_RenderW, CFG_RenderH)
                If Not ipnAlreadyOpen Then
                    Try : ipnDoc.Close(True) : Catch : End Try
                End If
                oDoc.Activate()
            End If
        End If
    Catch : End Try

' ==============================================================================
' SECTION 6: XỬ LÝ NÉT XANH ĐẬM & VẼ KÍCH THƯỚC PHỦ BÌ (CAD DIMENSIONS)
' ==============================================================================
oApp.StatusBarText = "🎨 Đang dập Nét Xanh Dương & Vẽ Kích Thước Phủ Bì CAD..."

' Log lỗi thay vì nuốt im lặng — hiển thị ở cuối nếu có sự cố
Dim renderErrors As New System.Collections.Generic.List(Of String)()

' Định nghĩa danh sách các frame cần xử lý (Dùng mảng chuỗi thuần túy)
' Format: {FilePath, ViewTitle, DimHorizValString, DimVertValString, HorizLabel, VertLabel}
Dim processTasks As New System.Collections.Generic.List(Of String())()

' 0. Wireframe 3D Topology (Đồng bộ nét xanh sạch sẽ cho ảnh sàn 3D)
Dim snapWireframe3D As String = System.IO.Path.Combine(snapshotDir, baseName & "_04_Wireframe3D_Topology_CheckMate.png")
If System.IO.File.Exists(snapWireframe3D) Then
    processTasks.Add(New String() {snapWireframe3D, "WIREFRAME 3D TOPOLOGY", "0", "0", "", ""})
End If

Dim snapWFFront As String = System.IO.Path.Combine(snapshotDir, baseName & "_16_Wireframe_Clean_Front.png")
If System.IO.File.Exists(snapWFFront) Then processTasks.Add(New String() {snapWFFront, "WIREFRAME FRONT ELEVATION", "0", "0", "", ""})

Dim snapWFTop As String = System.IO.Path.Combine(snapshotDir, baseName & "_17_Wireframe_Clean_Top.png")
If System.IO.File.Exists(snapWFTop) Then processTasks.Add(New String() {snapWFTop, "WIREFRAME TOP PLAN", "0", "0", "", ""})


' Tính toán kích thước phủ bì thực tế theo hướng chiếu của ViewCube:
Dim len_front_mm As Long = Math.Max(dx_mm, dz_mm) ' Chiều dài thân chính
Dim wid_side_mm  As Long = Math.Min(dx_mm, dz_mm) ' Chiều rộng đầu hồi
Dim hei_mm       As Long = dy_mm                  ' Chiều cao

' 1. Front View: Thể hiện chiều dài lớn nhất x Chiều cao
processTasks.Add(New String() {snapFront, "FRONT ELEVATION (HÌNH CHIẾU ĐỨNG)", len_front_mm.ToString(), hei_mm.ToString(), "L", "H"})
processTasks.Add(New String() {frameDir & "\FRAME_" & frontStartFrame.ToString("00000") & ".png", "FRONT ELEVATION", len_front_mm.ToString(), hei_mm.ToString(), "L", "H"})

' 2. Top View: Thể hiện chiều dài lớn nhất x Chiều rộng đầu hồi
processTasks.Add(New String() {snapTop, "TOP PLAN VIEW (HÌNH CHIẾU BẰNG)", len_front_mm.ToString(), wid_side_mm.ToString(), "L", "W"})
processTasks.Add(New String() {frameDir & "\FRAME_" & topStartFrame.ToString("00000") & ".png", "TOP PLAN VIEW", len_front_mm.ToString(), wid_side_mm.ToString(), "L", "W"})

' 3. Left View: Thể hiện chiều rộng đầu hồi x Chiều cao
processTasks.Add(New String() {snapLeft, "LEFT SIDE ELEVATION (HÌNH CHIẾU CẠNH TRÁI)", wid_side_mm.ToString(), hei_mm.ToString(), "W", "H"})
processTasks.Add(New String() {frameDir & "\FRAME_" & rightStartFrame.ToString("00000") & ".png", "LEFT SIDE ELEVATION", wid_side_mm.ToString(), hei_mm.ToString(), "W", "H"})

' MÀU XANH DƯƠNG ĐẬM SÂU CHUẨN BẢN VẼ: #043296 (R=4, G=50, B=150)
Dim targetR As Byte = 4
Dim targetG As Byte = 50
Dim targetB As Byte = 150

' Tỷ lệ co giãn font chữ và nét vẽ theo độ phân giải (1080p → 1.0, 4K → 2.0)
Dim resScale As Single = CSng(CFG_RenderH) / 1920.0F
If Not isVertical Then resScale = CSng(CFG_RenderH) / 1080.0F

For Each task In processTasks
    Dim fPath As String = task(0)
    Dim vTitle As String = task(1)
    Dim dHorizVal As Long = CLng(task(2))
    Dim dVertVal As Long = CLng(task(3))
    Dim hLbl As String = task(4)
    Dim vLbl As String = task(5)
    
    Try
        If System.IO.File.Exists(fPath) Then
            Dim imgBytes As Byte() = System.IO.File.ReadAllBytes(fPath)
            Using msIn As New System.IO.MemoryStream(imgBytes)
            Using rawBmp As New System.Drawing.Bitmap(msIn)
                Dim w As Integer = rawBmp.Width
                Dim h As Integer = rawBmp.Height
                
                ' Tạo Bitmap 32-bit ARGB độc lập chuẩn hóa để đảm bảo LockBits và GDI+ Graphics hoạt động 100% ổn định
                Using bmp As New System.Drawing.Bitmap(w, h, System.Drawing.Imaging.PixelFormat.Format32bppArgb)
                    Using gInit As System.Drawing.Graphics = System.Drawing.Graphics.FromImage(bmp)
                        gInit.DrawImage(rawBmp, 0, 0, w, h)
                    End Using
                    
                    Dim rect As New System.Drawing.Rectangle(0, 0, w, h)
                    Dim bmpData As System.Drawing.Imaging.BitmapData = bmp.LockBits(rect, System.Drawing.Imaging.ImageLockMode.ReadWrite, System.Drawing.Imaging.PixelFormat.Format32bppArgb)
                    
                    Dim ptr As IntPtr = bmpData.Scan0
                    Dim bytes As Integer = Math.Abs(bmpData.Stride) * h
                    Dim rgbValues(bytes - 1) As Byte
                    System.Runtime.InteropServices.Marshal.Copy(ptr, rgbValues, 0, bytes)
                    
                    Dim outValues As Byte() = DirectCast(rgbValues.Clone(), Byte())
                    Dim stride As Integer = Math.Abs(bmpData.Stride)
                    
                    Dim minX As Integer = w, maxX As Integer = 0
                    Dim minY As Integer = h, maxY As Integer = 0
                    
                    ' Quét pixel tìm viền biên mô hình & nhuộm màu Xanh Dương Deep Navy
                    Dim scanMarginX As Integer = CInt(w * 0.05)
                    Dim scanMarginY As Integer = CInt(h * 0.05)
                    
                    For y As Integer = scanMarginY To h - scanMarginY - 1
                        For x As Integer = scanMarginX To w - scanMarginX - 1
                            Dim idx As Integer = y * stride + x * 4
                            Dim b As Byte = rgbValues(idx)
                            Dim g As Byte = rgbValues(idx + 1)
                            Dim r As Byte = rgbValues(idx + 2)
                            
                            Dim brightnessSum As Integer = CInt(r) + CInt(g) + CInt(b)
                            
                            ' Chỉ ghi nhận Bounding Box khi là nét vẽ thực tế của mô hình
                            If brightnessSum < 450 Then
                                If x < minX Then minX = x
                                If x > maxX Then maxX = x
                                If y < minY Then minY = y
                                If y > maxY Then maxY = y
                            End If
                            
                            ' Nhuộm màu Xanh Dương Deep Navy ĐẬM ĐÀ, SẮC NÉT & KHỬ RĂNG CƯA
                            If brightnessSum < 580 Then
                                Dim normalizedDark As Double = (580.0 - CDbl(brightnessSum)) / 580.0
                                Dim darkFactor As Double = Math.Min(1.0, Math.Pow(normalizedDark, 0.42) * 1.45)
                                
                                Dim curB As Byte = outValues(idx)
                                Dim curG As Byte = outValues(idx + 1)
                                Dim curR As Byte = outValues(idx + 2)
                                
                                outValues(idx)     = CByte(Math.Min(255.0, CDbl(curB) * (1.0 - darkFactor) + CDbl(targetB) * darkFactor))
                                outValues(idx + 1) = CByte(Math.Min(255.0, CDbl(curG) * (1.0 - darkFactor) + CDbl(targetG) * darkFactor))
                                outValues(idx + 2) = CByte(Math.Min(255.0, CDbl(curR) * (1.0 - darkFactor) + CDbl(targetR) * darkFactor))
                                
                                ' Tăng cường độ dày cho tim nét chính
                                If brightnessSum < 380 Then
                                    Dim maxDilate As Integer = If(resScale >= 1.8F, 3, If(resScale >= 1.2F, 2, 1))
                                    For dStep As Integer = 1 To maxDilate
                                        Dim blendFactor As Double = If(dStep = 1, 0.85, If(dStep = 2, 0.60, 0.35))
                                        Dim invFactor As Double = 1.0 - blendFactor
                                        
                                        Dim offX As Integer = dStep * 4
                                        Dim offY As Integer = dStep * stride
                                        
                                        Dim d1 As Integer = idx + offX, d2 As Integer = idx - offX
                                        Dim d3 As Integer = idx + offY, d4 As Integer = idx - offY
                                        
                                        If d1 < bytes - 4 Then outValues(d1) = CByte(CDbl(outValues(d1)) * invFactor + CDbl(targetB) * blendFactor) : outValues(d1 + 1) = CByte(CDbl(outValues(d1 + 1)) * invFactor + CDbl(targetG) * blendFactor) : outValues(d1 + 2) = CByte(CDbl(outValues(d1 + 2)) * invFactor + CDbl(targetR) * blendFactor)
                                        If d2 >= 0 Then outValues(d2) = CByte(CDbl(outValues(d2)) * invFactor + CDbl(targetB) * blendFactor) : outValues(d2 + 1) = CByte(CDbl(outValues(d2 + 1)) * invFactor + CDbl(targetG) * blendFactor) : outValues(d2 + 2) = CByte(CDbl(outValues(d2 + 2)) * invFactor + CDbl(targetR) * blendFactor)
                                        If d3 < bytes - 4 Then outValues(d3) = CByte(CDbl(outValues(d3)) * invFactor + CDbl(targetB) * blendFactor) : outValues(d3 + 1) = CByte(CDbl(outValues(d3 + 1)) * invFactor + CDbl(targetG) * blendFactor) : outValues(d3 + 2) = CByte(CDbl(outValues(d3 + 2)) * invFactor + CDbl(targetR) * blendFactor)
                                        If d4 >= 0 Then outValues(d4) = CByte(CDbl(outValues(d4)) * invFactor + CDbl(targetB) * blendFactor) : outValues(d4 + 1) = CByte(CDbl(outValues(d4 + 1)) * invFactor + CDbl(targetG) * blendFactor) : outValues(d4 + 2) = CByte(CDbl(outValues(d4 + 2)) * invFactor + CDbl(targetR) * blendFactor)
                                    Next
                                End If
                            End If
                        Next
                    Next
                    
                    System.Runtime.InteropServices.Marshal.Copy(outValues, 0, ptr, bytes)
                    bmp.UnlockBits(bmpData)
                    
                    ' VẼ ĐƯỜNG KÍCH THƯỚC PHỦ BÌ (CAD DIMENSION OVERLAY) - CHỈ VẼ CHO CÁC HÌNH CHIẾU 2D (dHorizVal > 0)
                    If maxX > minX AndAlso maxY > minY AndAlso dHorizVal > 0 Then
                        Using gDraw As System.Drawing.Graphics = System.Drawing.Graphics.FromImage(bmp)
                            gDraw.SmoothingMode = System.Drawing.Drawing2D.SmoothingMode.AntiAlias
                            gDraw.TextRenderingHint = System.Drawing.Text.TextRenderingHint.ClearTypeGridFit
                            gDraw.InterpolationMode = System.Drawing.Drawing2D.InterpolationMode.HighQualityBicubic
                            gDraw.PixelOffsetMode = System.Drawing.Drawing2D.PixelOffsetMode.HighQuality
                            
                            Dim mainBlue As System.Drawing.Color = System.Drawing.Color.FromArgb(4, 50, 150)
                            
                            Using dimPen As New System.Drawing.Pen(mainBlue, Math.Max(2.5F, 3.0F * resScale))
                            Using extPen As New System.Drawing.Pen(System.Drawing.Color.FromArgb(140, 160, 190), Math.Max(1.5F, 2.0F * resScale))
                            Using fontDim As New System.Drawing.Font("Arial", Math.Max(16.0F, 24.0F * resScale), System.Drawing.FontStyle.Bold)
                            Using fontBadge As New System.Drawing.Font("Arial", Math.Max(14.0F, 22.0F * resScale), System.Drawing.FontStyle.Bold)
                            Using brushBlue As New System.Drawing.SolidBrush(mainBlue)
                            Using brushWhite As New System.Drawing.SolidBrush(System.Drawing.Color.White)
                            Using brushLightBlue As New System.Drawing.SolidBrush(System.Drawing.Color.FromArgb(240, 245, 255))
                            Using penBorder As New System.Drawing.Pen(mainBlue, Math.Max(1.5F, 2.0F * resScale))
                            Using penBadge As New System.Drawing.Pen(mainBlue, Math.Max(2.0F, 2.5F * resScale))
                                extPen.DashStyle = System.Drawing.Drawing2D.DashStyle.Dash
                                
                                ' 1. ĐƯỜNG KÍCH THƯỚC NGANG (HORIZONTAL DIMENSION) DƯỚI ĐÁY
                                Dim gapBottom As Integer = CInt(70 * resScale)
                                Dim dimY As Integer = Math.Min(h - CInt(90 * resScale), maxY + gapBottom)
                                gDraw.DrawLine(extPen, minX, maxY + CInt(15 * resScale), minX, dimY + CInt(25 * resScale))
                                gDraw.DrawLine(extPen, maxX, maxY + CInt(15 * resScale), maxX, dimY + CInt(25 * resScale))
                                gDraw.DrawLine(dimPen, minX, dimY, maxX, dimY)
                                
                                ' Mũi tên 2 đầu ngang
                                Dim arrowL As Integer = CInt(16 * resScale)
                                Dim arrowH As Integer = CInt(6 * resScale)
                                gDraw.FillPolygon(brushBlue, New System.Drawing.Point() {New System.Drawing.Point(minX, dimY), New System.Drawing.Point(minX + arrowL, dimY - arrowH), New System.Drawing.Point(minX + arrowL, dimY + arrowH)})
                                gDraw.FillPolygon(brushBlue, New System.Drawing.Point() {New System.Drawing.Point(maxX, dimY), New System.Drawing.Point(maxX - arrowL, dimY - arrowH), New System.Drawing.Point(maxX - arrowL, dimY + arrowH)})
                                
                                ' Nhãn kích thước ngang
                                Dim textH As String = hLbl & ": " & dHorizVal.ToString("#,##0") & " mm"
                                Dim sizeH As System.Drawing.SizeF = gDraw.MeasureString(textH, fontDim)
                                Dim posX As Single = (minX + maxX - sizeH.Width) / 2.0F
                                Dim posY As Single = dimY + CInt(18 * resScale)
                                gDraw.FillRectangle(brushWhite, posX - 10 * resScale, posY - 2 * resScale, sizeH.Width + 20 * resScale, sizeH.Height + 4 * resScale)
                                gDraw.DrawRectangle(penBorder, posX - 10 * resScale, posY - 2 * resScale, sizeH.Width + 20 * resScale, sizeH.Height + 4 * resScale)
                                gDraw.DrawString(textH, fontDim, brushBlue, posX, posY)
                                
                                ' 2. ĐƯỜNG KÍCH THƯỚC DỌC (VERTICAL DIMENSION) BÊN PHẢI
                                Dim gapRight As Integer = CInt(70 * resScale)
                                Dim dimX As Integer = Math.Min(w - CInt(120 * resScale), maxX + gapRight)
                                gDraw.DrawLine(extPen, maxX + CInt(15 * resScale), minY, dimX + CInt(25 * resScale), minY)
                                gDraw.DrawLine(extPen, maxX + CInt(15 * resScale), maxY, dimX + CInt(25 * resScale), maxY)
                                gDraw.DrawLine(dimPen, dimX, minY, dimX, maxY)
                                
                                ' Mũi tên 2 đầu đứng
                                Dim arrowL_V As Integer = CInt(16 * resScale)
                                Dim arrowH_V As Integer = CInt(6 * resScale)
                                gDraw.FillPolygon(brushBlue, New System.Drawing.Point() {New System.Drawing.Point(dimX, minY), New System.Drawing.Point(dimX - arrowH_V, minY + arrowL_V), New System.Drawing.Point(dimX + arrowH_V, minY + arrowL_V)})
                                gDraw.FillPolygon(brushBlue, New System.Drawing.Point() {New System.Drawing.Point(dimX, maxY), New System.Drawing.Point(dimX - arrowH_V, maxY - arrowL_V), New System.Drawing.Point(dimX + arrowH_V, maxY - arrowL_V)})
                                
                                ' Nhãn kích thước dọc (Xoay 90 độ)
                                Dim textV As String = vLbl & ": " & dVertVal.ToString("#,##0") & " mm"
                                Dim sizeV As System.Drawing.SizeF = gDraw.MeasureString(textV, fontDim)
                                Dim midVY As Single = (minY + maxY) / 2.0F
                                Dim posVX As Single = dimX + CInt(24 * resScale) + (sizeV.Height / 2.0F)
                                
                                Dim stateV As System.Drawing.Drawing2D.GraphicsState = gDraw.Save()
                                gDraw.TranslateTransform(posVX, midVY)
                                gDraw.RotateTransform(-90.0F)
                                
                                Dim rectVW As Single = sizeV.Width + 16.0F * resScale
                                Dim rectVH As Single = sizeV.Height + 4.0F * resScale
                                gDraw.FillRectangle(brushWhite, -rectVW / 2.0F, -rectVH / 2.0F, rectVW, rectVH)
                                gDraw.DrawRectangle(penBorder, -rectVW / 2.0F, -rectVH / 2.0F, rectVW, rectVH)
                                gDraw.DrawString(textV, fontDim, brushBlue, -sizeV.Width / 2.0F, -sizeV.Height / 2.0F)
                                gDraw.Restore(stateV)
                                
                                ' 3. THẺ TIÊU ĐỀ PHỦ BÌ TRÊN ĐẦU
                                Dim headerText As String = vTitle & "  |  " & hLbl & "=" & dHorizVal.ToString("#,##0") & " × " & vLbl & "=" & dVertVal.ToString("#,##0") & " mm"
                                Dim sizeBadge As System.Drawing.SizeF = gDraw.MeasureString(headerText, fontBadge)
                                Dim badgeW As Single = sizeBadge.Width + 40 * resScale
                                Dim badgeH As Single = sizeBadge.Height + 16 * resScale
                                Dim badgeX As Single = (w - badgeW) / 2.0F
                                Dim badgeY As Single = Math.Max(30.0F * resScale, CSng(minY - badgeH - 35.0F * resScale))
                                
                                gDraw.FillRectangle(brushLightBlue, badgeX, badgeY, badgeW, badgeH)
                                gDraw.DrawRectangle(penBadge, badgeX, badgeY, badgeW, badgeH)
                                gDraw.DrawString(headerText, fontBadge, brushBlue, badgeX + 20 * resScale, badgeY + 8 * resScale)
                            End Using : End Using : End Using : End Using : End Using : End Using : End Using : End Using : End Using
                        End Using ' gDraw
                    End If
                    
                    ' Xuất ảnh ra MemoryStream rồi ghi đè file đĩa cực sạch bằng File.WriteAllBytes
                    Using msOut As New System.IO.MemoryStream()
                        bmp.Save(msOut, System.Drawing.Imaging.ImageFormat.Png)
                        System.IO.File.WriteAllBytes(fPath, msOut.ToArray())
                    End Using
                End Using ' bmp
            End Using ' rawBmp
            End Using ' msIn
        End If
    Catch exImage As Exception
        renderErrors.Add(System.IO.Path.GetFileName(fPath) & ": " & exImage.Message)
    End Try
Next

' NHÂN BẢN SIÊU TỐC TỨC THÌ (0.01s): Copy frame đầu tiên đã vẽ DIM cho toàn bộ các frame giữ tĩnh
Dim srcFront As String = frameDir & "\FRAME_" & frontStartFrame.ToString("00000") & ".png"
If System.IO.File.Exists(srcFront) Then
    For fIdx As Integer = frontStartFrame + 1 To frontEndFrame
        Try : System.IO.File.Copy(srcFront, frameDir & "\FRAME_" & fIdx.ToString("00000") & ".png", True) : Catch : End Try
    Next
End If

Dim srcTop As String = frameDir & "\FRAME_" & topStartFrame.ToString("00000") & ".png"
If System.IO.File.Exists(srcTop) Then
    For fIdx As Integer = topStartFrame + 1 To topEndFrame
        Try : System.IO.File.Copy(srcTop, frameDir & "\FRAME_" & fIdx.ToString("00000") & ".png", True) : Catch : End Try
    Next
End If

Dim srcRight As String = frameDir & "\FRAME_" & rightStartFrame.ToString("00000") & ".png"
If System.IO.File.Exists(srcRight) Then
    For fIdx As Integer = rightStartFrame + 1 To rightEndFrame
        Try : System.IO.File.Copy(srcRight, frameDir & "\FRAME_" & fIdx.ToString("00000") & ".png", True) : Catch : End Try
    Next
End If

GoTo NormalComplete

' ==============================================================================
' ABORT HANDLER
' ==============================================================================
AbortRender:
    oApp.StatusBarText = "🛑 ĐÃ DỪNG TIẾN TRÌNH RENDER THEO LỆNH (ESC)!"
    Try
        oView.DisplayMode = DisplayModeEnum.kShadedWithEdgesRendering
        oView.ShowAmbientShadows = True
        oView.ShowObjectShadows  = True
        oView.ShowGroundShadows  = True
        oView.ShowGroundReflections = True
    Catch
    End Try
    oCam.Eye = tg.CreatePoint(orgEyeX, orgEyeY, orgEyeZ)
    oCam.Target = tg.CreatePoint(orgTgtX, orgTgtY, orgTgtZ)
    oCam.UpVector = tg.CreateUnitVector(orgUpX, orgUpY, orgUpZ)
    oCam.Perspective = orgPersp
    If orgPersp Then
        Try : oCam.PerspectiveAngle = orgPerspAng : Catch : End Try
    End If
    oCam.Apply() : oView.Update()
    MessageBox.Show("🛑 Đã dừng Render thành công và khôi phục góc nhìn ban đầu!", "WT3D", MessageBoxButtons.OK, MessageBoxIcon.Information)
    Exit Sub

' ==============================================================================
' HOÀN TẤT & GHÉP VIDEO
' ==============================================================================
NormalComplete:
    ' Khôi phục góc nhìn
    Try
        oView.DisplayMode = DisplayModeEnum.kShadedWithEdgesRendering
        oView.ShowAmbientShadows = True
        oView.ShowObjectShadows  = True
        oView.ShowGroundShadows  = True
        oView.ShowGroundReflections = True
    Catch
    End Try
    oCam.Eye = tg.CreatePoint(orgEyeX, orgEyeY, orgEyeZ)
    oCam.Target = tg.CreatePoint(orgTgtX, orgTgtY, orgTgtZ)
    oCam.UpVector = tg.CreateUnitVector(orgUpX, orgUpY, orgUpZ)
    oCam.Perspective = orgPersp
    If orgPersp Then
        Try : oCam.PerspectiveAngle = orgPerspAng : Catch : End Try
    End If
    oCam.Apply() : oView.Update()
    
    ' ✅ FIX: Hiển thị lỗi render ảnh nếu có (thay vì nuốt im lặng)
    If renderErrors.Count > 0 Then
        oApp.StatusBarText = "⚠️ Có " & renderErrors.Count & " ảnh gặp lỗi khi xử lý pixel/dimension."
        MessageBox.Show("⚠️ Một số ảnh gặp lỗi khi xử lý:" & vbCrLf & String.Join(vbCrLf, renderErrors.ToArray()), _
                        "WT3D - Cảnh Báo", MessageBoxButtons.OK, MessageBoxIcon.Warning)
    End If
    
    ' Ghép video qua FFmpeg & Đính kèm Thumbnail Cover Art (ViewCube Fit To View)
    ' ✅ FIX: Tìm ffmpeg động theo thư mục script, fallback sang hardcode
    Dim ffmpegExe As String = System.IO.Path.Combine(System.IO.Path.GetDirectoryName(oDoc.FullFileName), "..\Z_Tools\ffmpeg\ffmpeg.exe")
    If Not System.IO.File.Exists(ffmpegExe) Then
        ffmpegExe = "d:\WT3D_Project\Z_Tools\ffmpeg\ffmpeg.exe"
    End If
    Dim thumbCover As String = System.IO.Path.Combine(snapshotDir, baseName & "_01_Hero3D_Iso_TopRight.png")
    
    If Not System.IO.File.Exists(ffmpegExe) Then
        ' ✅ FIX: Cảnh báo rõ ràng thay vì im lặng chuyển nhánh
        MessageBox.Show("⚠️ Không tìm thấy ffmpeg tại:" & vbCrLf & ffmpegExe & vbCrLf & vbCrLf & _
                        "Các frame ảnh đã được xuất tại:" & vbCrLf & frameDir & vbCrLf & vbCrLf & _
                        "Để ghép video, hãy cài ffmpeg và đặt tại đường dẫn trên.", _
                        "WT3D - Thiếu FFmpeg", MessageBoxButtons.OK, MessageBoxIcon.Warning)
        Try : System.Diagnostics.Process.Start("explorer.exe", snapshotDir) : Catch : End Try
    Else
        Dim outMp4 As String = System.IO.Path.Combine(videoDir, baseName & "_EngineeringProjection_" & fullTag & ".mp4")
        
        ' ✅ FIX: Escape dấu nháy đơn trong tên file để tránh vỡ cú pháp PowerShell
        Dim safeFrameDir As String = frameDir.Replace("'", "''")
        Dim safeThumb As String = thumbCover.Replace("'", "''")
        Dim safeOut As String = outMp4.Replace("'", "''")
        Dim safeFfmpeg As String = ffmpegExe.Replace("'", "''")
        
        Dim psCmd As String
        If System.IO.File.Exists(thumbCover) Then
            ' Thumbnail ViewCube + CRF 16 medium → chất lượng cao, encode nhanh
            psCmd = "powershell.exe -ExecutionPolicy Bypass -WindowStyle Hidden -Command ""& '" & safeFfmpeg & "' -y -framerate " & CFG_FPS & " -i '" & safeFrameDir & "\FRAME_%05d.png' -i '" & safeThumb & "' -map 0:v -map 1:v -c:v:0 libx264 -preset medium -crf 16 -pix_fmt yuv420p -c:v:1 png -disposition:v:1 attached_pic '" & safeOut & "'; if (Test-Path '" & safeOut & "') { Remove-Item '" & safeFrameDir & "' -Recurse -Force }"""
        Else
            psCmd = "powershell.exe -ExecutionPolicy Bypass -WindowStyle Hidden -Command ""& '" & safeFfmpeg & "' -y -framerate " & CFG_FPS & " -i '" & safeFrameDir & "\FRAME_%05d.png' -c:v libx264 -preset medium -crf 16 -pix_fmt yuv420p '" & safeOut & "'; if (Test-Path '" & safeOut & "') { Remove-Item '" & safeFrameDir & "' -Recurse -Force }"""
        End If
        
        Try
            Dim sh As Object = CreateObject("WScript.Shell")
            sh.Run(psCmd, 0, True)
        Catch exFfmpeg As Exception
            renderErrors.Add("FFmpeg: " & exFfmpeg.Message)
        End Try
        
        ' Dập 'Bản Quyền Sàn 3D' tự động cho toàn bộ bộ ảnh Snapshot xuất ra
        Dim pyWatermarkScript As String = System.IO.Path.Combine(System.IO.Path.GetDirectoryName(oDoc.FullFileName), "..\Z_Tools\Apply_Marketplace_Watermark.py")
        If Not System.IO.File.Exists(pyWatermarkScript) Then
            pyWatermarkScript = "d:\WT3D_Project\Z_Tools\Apply_Marketplace_Watermark.py"
        End If
        If System.IO.File.Exists(pyWatermarkScript) AndAlso System.IO.Directory.Exists(snapshotDir) Then
            Dim safePyScript As String = pyWatermarkScript.Replace("'", "''")
            Dim safeSnapDir As String = snapshotDir.Replace("'", "''")
            Dim psWatermarkCmd As String = "powershell.exe -ExecutionPolicy Bypass -WindowStyle Hidden -Command ""python '" & safePyScript & "' '" & safeSnapDir & "'"""
            Try
                Dim shWmk As Object = CreateObject("WScript.Shell")
                shWmk.Run(psWatermarkCmd, 0, True)
            Catch : End Try
        End If
        
        Dim isEngineSilent As Boolean = False
        If SharedVariable.Exists("WT3D_SILENT_MODE") Then
            Try : isEngineSilent = CBool(SharedVariable("WT3D_SILENT_MODE")) : Catch : End Try
        End If
        If SharedVariable.Exists("WT3D_BATCH_MODE") Then
            Try
                If CBool(SharedVariable("WT3D_BATCH_MODE")) Then isEngineSilent = True
            Catch
            End Try
        End If

        If Not isEngineSilent Then
            If isOpenFolder Then
                Try : System.Diagnostics.Process.Start("explorer.exe", videoDir) : Catch : End Try
                Try : System.Diagnostics.Process.Start("explorer.exe", snapshotDir) : Catch : End Try
            End If
            
            MessageBox.Show("🎉 XUẤT VIDEO & BỘ ẢNH SNAPSHOT THÀNH CÔNG!" & vbCrLf & vbCrLf & _
                            "• Định dạng: " & fullTag & " (" & CFG_RenderW & "x" & CFG_RenderH & ")" & vbCrLf & _
                            "• Thumbnail Poster Video: Khóa cứng chuẩn ViewCube Fit To View." & vbCrLf & _
                            "• Trọn bộ 19+ Ảnh Snapshot 360 độ (Shaded, Blueprint, Clay, CheckMate)." & vbCrLf & _
                            "• Dáng mô hình: " & If(postureMode = 1, "Dáng Nằm Ngang (+26°/+30°)", If(postureMode = 2, "Dáng Cao Đứng (+10°/+12°)", "Dáng Cân Đối (+15°/+18°)")) & vbCrLf & _
                            "• Kích thước tổng thể: " & dx_mm & " × " & dz_mm & " × " & dy_mm & " mm (Dài × Rộng × Cao)" & vbCrLf & _
                            "• Video lưu tại: " & outMp4 & vbCrLf & _
                            "• Ảnh Snapshots tại: " & snapshotDir, "WT3D Studio Engine", MessageBoxButtons.OK, MessageBoxIcon.Information)
        End If
    End If

    End Sub
End Class
