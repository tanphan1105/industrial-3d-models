' ==============================================================================
' WT3D STUDIO RIG: B0_SET_TWO_LIGHTS_STUDIO.iLogicVb
' TIÊU CHUẨN: TWO LIGHTS VIEW SPACE (FOLLOW VIEWCUBE) + ALL SHADOWS + FIT TO VIEW
' ÁNH SÁNG MẶT TRƯỚC RỰC RỠ, RÕ NÉT (BRIGHTNESS 72%, AMBIENCE 28%, FRONT VIEW SPACE)
' PHÙ HỢP CẢ PART (.IPT) VÀ ASSEMBLY (.IAM)
' ==============================================================================

AddReference "System.Windows.Forms"
AddReference "System.Private.Windows.Core"
AddReference "System.Drawing"

Imports System
Imports System.Drawing
Imports System.Runtime.InteropServices
Imports System.Windows.Forms
Imports Inventor

Public Class ThisRule
    <DllImport("user32.dll")>
    Private Shared Function GetAsyncKeyState(ByVal vKey As Integer) As Short
    End Function
    Private Const VK_ESCAPE As Integer = &H1B

    Private Function CheckEscape() As Boolean
        Try
            System.Windows.Forms.Application.DoEvents()
            If (GetAsyncKeyState(VK_ESCAPE) And &H8000) <> 0 OrElse GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Dim oApp As Inventor.Application = ThisApplication
        Dim oDoc As Document = oApp.ActiveDocument
        If oDoc Is Nothing Then
            MessageBox.Show("Vui long mo mot chi tiet (.ipt) hoac cum lap (.iam) trong Inventor!", "WT3D", MessageBoxButtons.OK, MessageBoxIcon.Warning)
            Exit Sub
        End If

        Dim isPartDoc As Boolean = (TypeOf oDoc Is PartDocument)
        Dim isAsmDoc As Boolean = (TypeOf oDoc Is AssemblyDocument)

        If Not isPartDoc AndAlso Not isAsmDoc Then
            MessageBox.Show("Tai lieu hien tai khong phai la Part (.ipt) hoac Assembly (.iam)!", "WT3D", MessageBoxButtons.OK, MessageBoxIcon.Warning)
            Exit Sub
        End If

        Dim tg As TransientGeometry = oApp.TransientGeometry
        Dim oView As Inventor.View = oApp.ActiveView
        If oView Is Nothing Then Exit Sub

        Try
            oApp.SilentOperation = True

            ' ==============================================================================
            ' 1. DỌN DẸP HIỂN THỊ TRIỆT ĐỂ (TẮT TOÀN BỘ MẶT PHẲNG, TRỤC, SKETCH)
            ' ==============================================================================
            Try
                Dim ctrlDef As ControlDefinition = oApp.CommandManager.ControlDefinitions.Item("AppAllWorkFeaturesCmd")
                If ctrlDef IsNot Nothing AndAlso ctrlDef.Pressed Then
                    ctrlDef.Execute()
                End If
            Catch : End Try

            Try
                oDoc.ObjectVisibility.AllWorkFeatures = False
                oDoc.ObjectVisibility.UserWorkPlanes = False
                oDoc.ObjectVisibility.OriginWorkPlanes = False
                oDoc.ObjectVisibility.UserWorkAxes = False
                oDoc.ObjectVisibility.OriginWorkAxes = False
                oDoc.ObjectVisibility.UserWorkPoints = False
                oDoc.ObjectVisibility.OriginWorkPoints = False
                oDoc.ObjectVisibility.OriginWorkFeatures = False
                oDoc.ObjectVisibility.Sketches = False
                oDoc.ObjectVisibility.Sketches3D = False
                oDoc.ObjectVisibility.WeldmentSymbols = False
                oDoc.ObjectVisibility.ConstructionSurfaces = False
            Catch : End Try

            ' ==============================================================================
            ' 2. TÌM VÀ KÍCH HOẠT LIGHTING STYLE "TWO LIGHTS"
            ' ==============================================================================
            Dim oStyles As LightingStyles = Nothing
            If isPartDoc Then
                oStyles = CType(oDoc, PartDocument).LightingStyles
            ElseIf isAsmDoc Then
                oStyles = CType(oDoc, AssemblyDocument).LightingStyles
            End If

            Dim targetLs As LightingStyle = Nothing

            If oStyles IsNot Nothing Then
                Try : targetLs = oStyles.Item("Two Lights") : Catch : End Try

                If targetLs Is Nothing Then
                    For Each ls As LightingStyle In oStyles
                        If CheckEscape() Then Exit Sub
                        SafeYield(5)
                        If ls.Name.Equals("Two Lights", StringComparison.OrdinalIgnoreCase) Then
                            targetLs = ls
                            Exit For
                        End If
                    Next
                End If

                If targetLs Is Nothing Then
                    For Each ls As LightingStyle In oStyles
                        If CheckEscape() Then Exit Sub
                        SafeYield(5)
                        If ls.Name.ToLower().Contains("two") OrElse ls.Name.Contains("2") Then
                            targetLs = ls
                            Exit For
                        End If
                    Next
                End If

                If targetLs IsNot Nothing Then
                    Try
                        If targetLs.StyleLocation = StyleLocationEnum.kLibraryStyleLocation Then
                            targetLs.ConvertToLocal()
                        End If
                    Catch : End Try

                    If isPartDoc Then
                        CType(oDoc, PartDocument).ActiveLightingStyle = targetLs
                    ElseIf isAsmDoc Then
                        CType(oDoc, AssemblyDocument).ActiveLightingStyle = targetLs
                    End If
                End If
            End If

            ' ==============================================================================
            ' 3. CẤU HÌNH HƯỚNG ÁNH SÁNG RỌI TRỰC DIỆN MẶT TRƯỚC (BRIGHTNESS 72%, AMBIENCE 28%)
            ' ==============================================================================
            Try
                Dim curStyle As LightingStyle = Nothing
                If isPartDoc Then
                    curStyle = CType(oDoc, PartDocument).ActiveLightingStyle
                ElseIf isAsmDoc Then
                    curStyle = CType(oDoc, AssemblyDocument).ActiveLightingStyle
                End If

                If curStyle IsNot Nothing Then
                    ' ĐẶT HƯỚNG ÁNH SÁNG / BÓNG ĐỔ: ABOVE (Chiếu từ trên xuống)
                    Try : curStyle.ShadowDirection = ShadowDirectionEnum.kAboveShadowDirection : Catch : End Try
                    Try : curStyle.ShadowDensity = 52.0 : Catch : End Try            ' Độ đậm bóng đổ sàn 52% (bóng mờ êm dịu chuẩn Anh Tấn)
                    Try : curStyle.ShadowSoftness = 50.0 : Catch : End Try           ' Độ mềm 50% (khuếch tán tự nhiên)
                    Try : curStyle.AmbientShadowIntensity = 18.0 : Catch : End Try   ' Ambient Shadows 18% (êm ái khe kẽ)

                    ' CẤU HÌNH 2 ĐÈN CHUẨN TỶ LỆ VÀNG: HIGHLIGHT SẮC NÉT & VIỀN BÓNG BẢY
                    Dim lNum As Integer = 1
                    For Each lt As Light In curStyle.Lights
                        If CheckEscape() Then Exit Sub
                        SafeYield(5)

                        If lNum = 1 Then
                            ' Light 1: Key Light 115% (Rọi góc 3/4 mặt trước, tạo điểm sáng specular lấp lánh trên bề mặt cong)
                            Try : lt.On = True : Catch : End Try
                            Try : lt.LightType = LightTypeEnum.kViewSpaceLight : Catch : End Try
                            Try : lt.Color = oApp.TransientObjects.CreateColor(255, 253, 248) : Catch : End Try
                            Try : lt.Intensity = 1.15 : Catch : End Try
                            Try : lt.Direction = tg.CreateVector(0.380000, -0.320000, -0.865000) : Catch : End Try
                        ElseIf lNum = 2 Then
                            ' Light 2: Fill & Rim Light 65% (Bù sáng mặt đứng và hắt viền sáng óng ả)
                            Try : lt.On = True : Catch : End Try
                            Try : lt.LightType = LightTypeEnum.kViewSpaceLight : Catch : End Try
                            Try : lt.Color = oApp.TransientObjects.CreateColor(245, 250, 255) : Catch : End Try
                            Try : lt.Intensity = 0.65 : Catch : End Try
                            Try : lt.Direction = tg.CreateVector(-0.420000, -0.220000, -0.885000) : Catch : End Try
                        Else
                            Try : lt.On = False : Catch : End Try
                        End If
                        lNum += 1
                    Next
                End If
            Catch : End Try

            ' ==============================================================================
            ' 4. THIẾT LẬP NỀN LIGHT VÀ GRADIENT ĐỒNG BỘ CHUẨN STUDIO
            ' ==============================================================================
            Try
                Dim appOpts As Inventor.ColorSchemes = oApp.ColorSchemes
                For Each cs As ColorScheme In appOpts
                    If CheckEscape() Then Exit Sub
                    If cs.Name.Equals("Light", StringComparison.OrdinalIgnoreCase) Then
                        cs.Activate()
                        Try : cs.ReflectionEnvironmentFilename = "studio_02.dds" : Catch : End Try
                        Exit For
                    End If
                Next
            Catch : End Try

            Try : oApp.ColorSchemes.BackgroundType = BackgroundTypeEnum.kGradientBackgroundType : Catch : End Try
            Try : oView.DisplayMode = DisplayModeEnum.kShadedWithEdgesRendering : Catch : End Try
            Try : oView.ShowGroundShadows = True : Catch : End Try
            Try : oView.ShowAmbientShadows = True : Catch : End Try
            Try : oView.ShowObjectShadows = True : Catch : End Try
            Try : oView.ShowGroundReflections = False : Catch : End Try

            ' Chuyển sang phối cảnh 3D Perspective có tụ & Tự động căn vừa khung nhìn (Fit to View)
            Try
                Dim oCam As Camera = oView.Camera
                If Not oCam.Perspective Then
                    oCam.Perspective = True
                End If
                oCam.Fit()
                oCam.ApplyWithoutTransition()
            Catch : End Try

            Try : oApp.DisplayOptions.DisplayQuality = DisplayQualityEnum.kSmootherDisplayQuality : Catch : End Try
            Try : oApp.DisplayOptions.AntiAliasing = True : Catch : End Try
            Try : oApp.DisplayOptions.SmoothLines = True : Catch : End Try

            ' ==============================================================================
            ' 5. TỰ ĐỘNG HIỆU CHỈNH ĐỘ BÓNG VẬT LIỆU (HIGH GLOSS & HIGH REFLECTIVITY)
            ' ==============================================================================
            Dim docsToProcess As New System.Collections.Generic.List(Of Document)()
            docsToProcess.Add(oDoc)

            If isAsmDoc Then
                Try
                    For Each refDoc As Document In oDoc.AllReferencedDocuments
                        If TypeOf refDoc Is PartDocument Then docsToProcess.Add(refDoc)
                    Next
                Catch : End Try
            End If

            For Each targetDoc As Document In docsToProcess
                If CheckEscape() Then Exit Sub
                SafeYield(5)

                Try
                    Dim oAssets As Assets = targetDoc.Assets
                    For Each oAsset As Asset In oAssets
                        If CheckEscape() Then Exit Sub

                        Dim nm As String = ""
                        Try : nm = oAsset.DisplayName.ToLower() : Catch : Continue For : End Try

                        Dim gloss As Double = -1
                        Dim refl0 As Double = -1
                        Dim refl90 As Double = -1
                        Dim metallic As Double = -1
                        Dim clearcoat As Double = 0.0

                        If nm.Contains("inox") OrElse nm.Contains("stainless") OrElse nm.Contains("steel") OrElse nm.Contains("thép") OrElse nm.Contains("chrome") OrElse nm.Contains("nickel") Then
                            gloss     = 0.92
                            refl0     = 0.72
                            refl90    = 0.98
                            metallic  = 1.00
                            clearcoat = 0.45
                        ElseIf nm.Contains("nhôm") OrElse nm.Contains("aluminum") OrElse nm.Contains("aluminium") OrElse nm.Contains("alum") Then
                            gloss     = 0.84
                            refl0     = 0.58
                            refl90    = 0.92
                            metallic  = 1.00
                            clearcoat = 0.35
                        ElseIf nm.Contains("đồng") OrElse nm.Contains("brass") OrElse nm.Contains("bronze") OrElse nm.Contains("copper") Then
                            gloss     = 0.88
                            refl0     = 0.65
                            refl90    = 0.95
                            metallic  = 1.00
                            clearcoat = 0.40
                        ElseIf nm.Contains("composite") OrElse nm.Contains("frp") OrElse nm.Contains("cột") OrElse nm.Contains("bồn") Then
                            gloss     = 0.82
                            refl0     = 0.35
                            refl90    = 0.88
                            metallic  = 0.00
                            clearcoat = 0.60
                        ElseIf nm.Contains("pvc") OrElse nm.Contains("hdpe") OrElse nm.Contains("upvc") OrElse nm.Contains("pp") OrElse nm.Contains("nhựa") OrElse nm.Contains("plastic") Then
                            gloss     = 0.68
                            refl0     = 0.16
                            refl90    = 0.65
                            metallic  = 0.00
                            clearcoat = 0.35
                        ElseIf nm.Contains("sơn") OrElse nm.Contains("paint") OrElse nm.Contains("powder") OrElse nm.Contains("epoxy") OrElse nm.Contains("coat") Then
                            gloss     = 0.72
                            refl0     = 0.16
                            refl90    = 0.65
                            metallic  = 0.00
                            clearcoat = 0.55
                        ElseIf nm.Contains("thủy tinh") OrElse nm.Contains("glass") OrElse nm.Contains("acrylic") OrElse nm.Contains("kính") Then
                            gloss     = 0.99
                            refl0     = 0.10
                            refl90    = 0.99
                            metallic  = 0.00
                            clearcoat = 0.80
                        ElseIf nm.Contains("gang") OrElse nm.Contains("iron") OrElse nm.Contains("cast") OrElse nm.Contains("carbon") OrElse nm.Contains("sắt") Then
                            gloss     = 0.48
                            refl0     = 0.25
                            refl90    = 0.58
                            metallic  = 1.00
                            clearcoat = 0.15
                        ElseIf nm.Contains("cao su") OrElse nm.Contains("rubber") OrElse nm.Contains("gasket") OrElse nm.Contains("oring") OrElse nm.Contains("epdm") OrElse nm.Contains("viton") Then
                            gloss     = 0.20
                            refl0     = 0.03
                            refl90    = 0.18
                            metallic  = 0.00
                            clearcoat = 0.00
                        End If

                        If gloss >= 0 Then
                            Try
                                Dim propG As AssetValue = oAsset("generic_glossiness")
                                If propG IsNot Nothing Then CType(propG, FloatAssetValue).Value = gloss
                            Catch : End Try
                            Try
                                Dim propR0 As AssetValue = oAsset("generic_reflectivity_at_0deg")
                                If propR0 IsNot Nothing Then CType(propR0, FloatAssetValue).Value = refl0
                            Catch : End Try
                            Try
                                Dim propR90 As AssetValue = oAsset("generic_reflectivity_at_90deg")
                                If propR90 IsNot Nothing Then CType(propR90, FloatAssetValue).Value = refl90
                            Catch : End Try
                            Try
                                Dim propM As AssetValue = oAsset("generic_metallic")
                                If propM IsNot Nothing Then CType(propM, FloatAssetValue).Value = metallic
                            Catch : End Try
                            Try
                                Dim propCc As AssetValue = oAsset("generic_clearcoat")
                                If propCc IsNot Nothing Then CType(propCc, FloatAssetValue).Value = clearcoat
                            Catch : End Try
                        End If
                    Next
                    Try : targetDoc.Update() : Catch : End Try
                Catch : End Try
            Next

            Try : oDoc.Update() : Catch : End Try
            Try : oView.Update() : Catch : End Try

        Catch ex As Exception
            MessageBox.Show("Loi phat sinh: " & ex.Message, "Loi Two Lights Studio", MessageBoxButtons.OK, MessageBoxIcon.Error)
        Finally
            oApp.SilentOperation = False
        End Try

        ' ==============================================================================
        ' 6. THÔNG BÁO HOÀN TẤT THIẾT LẬP TWO LIGHTS STUDIO
        ' ==============================================================================
        MessageBox.Show("🌟 ĐÃ CÂN BẰNG ÁNH SÁNG & CHỐNG CHÓI CHO TWO LIGHTS STUDIO!" & vbCrLf & _
                        "━━━━━━━━━━━━━━━━━━━━━━━━━━━━━━━━━━━━━━━━━━━━━━━━━" & vbCrLf & _
                        "• Độ sáng tổng thể (Brightness): 72% (Sáng rõ, tươi tắn, không tối xỉn)" & vbCrLf & _
                        "• Độ no sáng vùng tối (Ambience): 28% (Mặt trước sáng đều, rõ chi tiết)" & vbCrLf & _
                        "• Ánh sáng View Space: 100% bám theo ViewCube (Xoay góc nào cũng sáng rõ)
• Đèn chính (Key): 105% | Đèn phụ (Fill): 70% | Rọi trực diện mặt trước | Tự động Fit to View" & vbCrLf & _
                        "• Độ đậm bóng đổ: 52% (Bóng sàn vững chãi, mềm mại)" & vbCrLf & _
                        "• Nền Studio: Đồng bộ Color Scheme 'Light' + Kiểu nền 'Gradient' (studio_02.dds)" & vbCrLf & _
                        "• Độ bóng vật liệu: Satin chuẩn Inox (78%), Đồng (75%), Composite (65%), PVC (45%)", _
                        "WT3D Two Lights Studio Rig", MessageBoxButtons.OK, MessageBoxIcon.Information)
    End Sub
End Class
