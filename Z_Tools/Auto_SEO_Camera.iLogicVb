AddReference "PresentationCore"
AddReference "WindowsBase"
AddReference "System.Drawing"
AddReference "System.Private.Windows.GdiPlus"
AddReference "System.Windows.Forms"
AddReference "System.Private.Windows.Core"

Imports System.Windows.Input

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Try
            Dim oDoc As Inventor.Document = ThisDoc.Document
            Dim oView As Inventor.View = ThisApplication.ActiveView
            Dim oCam As Inventor.Camera = oView.Camera
            Dim originalDisplayMode As DisplayModeEnum = oView.DisplayMode

            Dim docFullName As String = oDoc.FullFileName
            Dim docDir As String = System.IO.Path.GetDirectoryName(docFullName)
            Dim baseName As String = System.IO.Path.GetFileNameWithoutExtension(docFullName)
            Dim masterDir As String = "d:\WT3D_Project"

            ' Dynamic Project Root Resolution
            Dim projectDir As String = docDir
            If docDir.ToLower().EndsWith("\01_assemblies") OrElse docDir.ToLower().EndsWith("\02_parts") OrElse docDir.ToLower().EndsWith("\03_drawings_2d") Then
                projectDir = System.IO.Directory.GetParent(docDir).FullName
            End If

            Dim mediaDir As String = System.IO.Path.Combine(projectDir, "06_Renders_and_Media")
            Dim savePath As String = System.IO.Path.Combine(mediaDir, "02_Images_4K_Previews\16_9_Landscape")
            Dim savePathPortrait As String = System.IO.Path.Combine(mediaDir, "02_Images_4K_Previews\9_16_Portrait")

            If Not System.IO.Directory.Exists(savePath) Then System.IO.Directory.CreateDirectory(savePath)
            If Not System.IO.Directory.Exists(savePathPortrait) Then System.IO.Directory.CreateDirectory(savePathPortrait)

            ' =======================================================
            ' TINH TOAN KICH THUOC BAO LOI (B2B SEO DIMENSIONS ENGINE)
            ' =======================================================
            Dim rBox As Box = Nothing
            If oDoc.DocumentType = DocumentTypeEnum.kAssemblyDocumentObject Then
                Dim asm As AssemblyDocument = CType(oDoc, AssemblyDocument)
                rBox = asm.ComponentDefinition.RangeBox
            End If



            Dim Lx As Integer = 0 : Dim Ly As Integer = 0 : Dim Lz As Integer = 0
            Dim sizeLabel As String = ""
            If rBox IsNot Nothing Then
                ' Đổi cm sang mm
                Lx = Math.Round((rBox.MaxPoint.X - rBox.MinPoint.X) * 10)
                Ly = Math.Round((rBox.MaxPoint.Y - rBox.MinPoint.Y) * 10) ' Cao
                Lz = Math.Round((rBox.MaxPoint.Z - rBox.MinPoint.Z) * 10)
                Dim lenMM As Integer = Math.Max(Lx, Lz)
                Dim widMM As Integer = Math.Min(Lx, Lz)
                sizeLabel = lenMM & "|" & widMM & "|" & Ly
            End If

            ' --- 1. SET ÁNH SÁNG, PHÔNG NỀN & DỌN DẸP RÁC HIỂN THỊ ---
            Try
                ' Tự động càn quét dọn dẹp mọi mặt phẳng cam (Work Planes), trục, và phác thảo (Sketches)
                oDoc.ObjectVisibility.AllWorkFeatures = False
                oDoc.ObjectVisibility.Sketches = False
                oDoc.ObjectVisibility.Sketches3D = False
            Catch
            End Try

            ' ÉP BUỘC SHADED WITH EDGES NHƯ ĐÃ THỐNG NHẤT
            oView.DisplayMode = DisplayModeEnum.kShadedWithEdgesRendering
            oView.Update()

            oView.ShowAmbientShadows = True
            oView.ShowObjectShadows = True ' Bóng đổ của ống/các chi tiết lên thân máy (Tạo độ sâu vật lý 3D)
            oView.ShowGroundShadows = True ' Bóng đổ xuống sàn (Chống cảm giác lơ lửng, tạo sức nặng Công Nghiệp)
            oView.ShowGroundReflections = False ' Tắt bóng kính phản chiếu vì nó làm rác bản vẽ kỹ thuật

            ' KẾT THỪA LÕI ÁNH SÁNG TỪ MAXSKILLS V4.1 (PHOTO BOOTH)
            Try
                oDoc.ActiveLightingStyle = oDoc.LightingStyles.Item("Photo Booth")
            Catch
                Try : oDoc.ActiveLightingStyle = oDoc.LightingStyles.Item("Empty Lab") : Catch : End Try
            End Try

            ' Ép buộc Nền chuyển sang màu Trắng (Solid) thay vì Gradient
            ThisApplication.ColorSchemes.BackgroundType = BackgroundTypeEnum.kGradientBackgroundType

            ' NÂNG CẤP "NHỨC NÁCH": ĐỘ PHÂN GIẢI 4K SIÊU NÉT (ULTRA HD 2160p)
            ' Khách hàng gõ Kính Lúp phóng to soi từng cái ren ốc cũng không hột/vỡ. Tăng 200% Tỷ lệ chốt Sale!
            Dim resWidth As Integer = 3840
            Dim resHeight As Integer = 2160
            Dim camW As Double
            Dim camH As Double

            ' =======================================================
            ' CHỤP ẢNH 0: GÓC MÁY ĐẤT NHÌN LÊN (LOW ANGLE HERO - HÙNG VĨ)
            ' Camera đặt dưới chân thiết bị, ngước lên nhìn - tạo cảm giác khổng lồ, áp đảo
            ' =======================================================
            Try
                Dim tg As TransientGeometry = ThisApplication.TransientGeometry
                If rBox IsNot Nothing Then
                    Dim cx As Double = (rBox.MinPoint.X + rBox.MaxPoint.X) / 2
                    Dim cy As Double = (rBox.MinPoint.Y + rBox.MaxPoint.Y) / 2
                    Dim cz As Double = (rBox.MinPoint.Z + rBox.MaxPoint.Z) / 2
                    Dim mH As Double = rBox.MaxPoint.Y - rBox.MinPoint.Y  ' Chiều cao model (cm)
                    Dim mW As Double = Math.Max(rBox.MaxPoint.X - rBox.MinPoint.X, rBox.MaxPoint.Z - rBox.MinPoint.Z)

                    ' Đặt máy ảnh ở VỊ TRÍ THẤP - Ngang tầm đáy thiết bị, kéo ra trước xa
                    Dim eyePt As Inventor.Point = tg.CreatePoint(
                        cx + mW * 0.9,              ' Lệch sang phải 90% độ rộng
                        rBox.MinPoint.Y - mH * 0.1, ' Thấp hơn đáy thiết bị 10% chiều cao
                        cz + mW * 1.1               ' Kéo ra trước 110% độ rộng
                    )
                    ' Ngắm vào điểm TRÊN ĐỈNH thiết bị để ánh mắt máy ảnh ngước lên cao
                    Dim targetPt As Inventor.Point = tg.CreatePoint(cx, rBox.MaxPoint.Y * 0.85, cz)
                    Dim upVec As Inventor.UnitVector = tg.CreateUnitVector(0, 1, 0) ' Trục Y thẳng đứng

                    oCam.Perspective = True
                    oCam.Eye = eyePt
                    oCam.Target = targetPt
                    oCam.UpVector = upVec
                    oCam.GetExtents(camW, camH)
                    oCam.SetExtents(camW * 0.80, camH * 0.80)
                    oCam.Apply()
                    oCam.SaveAsBitmap(savePath & "\" & baseName & "_00_LowAngle_Hero.png", resWidth, resHeight)

                If CheckEscape() Then
                    ThisApplication.StatusBarText = "🛑 ĐÃ DỪNG TIẾN TRÌNH THEO LỆNH (GIỮ PHÍM ESC)!"
                    Exit Sub
                End If
                SafeYield(20)
                Else
                    ' Fallback: nếu không lấy được rBox, dùng Fit() bình thường
                    oCam.Perspective = True
                    oCam.ViewOrientationType = ViewOrientationTypeEnum.kIsoTopRightViewOrientation
                    oCam.Fit()
                    oCam.GetExtents(camW, camH)
                    oCam.SetExtents(camW * 0.75, camH * 0.75)
                    oCam.Apply()
                    oCam.SaveAsBitmap(savePath & "\" & baseName & "_00_LowAngle_Hero.png", resWidth, resHeight)

                If CheckEscape() Then
                    ThisApplication.StatusBarText = "🛑 ĐÃ DỪNG TIẾN TRÌNH THEO LỆNH (GIỮ PHÍM ESC)!"
                    Exit Sub
                End If
                SafeYield(20)
                End If
            Catch
                ' Nuốt lỗi, chụp ảnh tiếp theo
            End Try

            ' =======================================================
            ' CHỤP ẢNH 1: TỔNG THỂ (HERO THUMBNAIL) CÓ MARGIN THỞ
            ' =======================================================
            oCam.Perspective = True ' Bật hiệu ứng tụ mắt người (Làm cụm RO nhìn khổng lồ, áp đảo)
            oCam.ViewOrientationType = ViewOrientationTypeEnum.kIsoTopRightViewOrientation
            oCam.Fit()
            oCam.GetExtents(camW, camH)
            oCam.SetExtents(camW * 0.75, camH * 0.75) ' Ép Zoom In 25% để mô hình cao chót vót lấp đầy chiều cao ảnh 16:9
            oCam.Apply()
            oCam.SaveAsBitmap(savePath & "\" & baseName & "_01_Overall_Hero.png", resWidth, resHeight)

                If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 2 & 3: GÓC MẶT TRÁI CHÉO LÊN & MẶT BẰNG TOP
            ' =======================================================
            oCam.ViewOrientationType = ViewOrientationTypeEnum.kIsoTopLeftViewOrientation
            oCam.Fit()
            oCam.GetExtents(camW, camH)
            oCam.SetExtents(camW * 0.75, camH * 0.75)
            oCam.Apply()
            oCam.SaveAsBitmap(savePath & "\" & baseName & "_02_Piping_Routing.png", resWidth, resHeight)

                If CheckEscape() Then
                    ThisApplication.StatusBarText = "🛑 ĐÃ DỪNG TIẾN TRÌNH THEO LỆNH (GIỮ PHÍM ESC)!"
                    Exit Sub
                End If
                SafeYield(20)

            oCam.ViewOrientationType = ViewOrientationTypeEnum.kTopViewOrientation
            oCam.Perspective = True ' Ép về Trực Giao phẳng lì (chuẩn Layout Kỹ Thuật)
            oCam.Fit()
            oCam.GetExtents(camW, camH)
            oCam.SetExtents(camW * 1.08, camH * 1.08) ' Mặt top phình ngang nên lùi 8% cho an toàn
            oCam.Apply()
            Dim topImgPath As String = savePath & "\" & baseName & "_03_Top_Plan_Layout.png"
            oCam.SaveAsBitmap(topImgPath, resWidth, resHeight)

                If CheckEscape() Then
                    ThisApplication.StatusBarText = "🛑 ĐÃ DỪNG TIẾN TRÌNH THEO LỆNH (GIỮ PHÍM ESC)!"
                    Exit Sub
                End If
                SafeYield(20)

            ' =======================================================
            ' TỰ ĐỘNG ĐO KÍCH THƯỚC TRÊN 3D ĐẨY VÀO CLIPBOARD (SEO METADATA)
            ' =======================================================
            Try
                ' 1. Quét tọa độ Bounding Box lớn nhất của Mô hình 
                Dim boxRef As Inventor.Box = oDoc.ComponentDefinition.RangeBox
                ' Chuyển đổi sang Milimet (Inventor xài cm)
                Dim L_mm As Integer = Math.Round((boxRef.MaxPoint.X - boxRef.MinPoint.X) * 10)
                Dim W_mm As Integer = Math.Round((boxRef.MaxPoint.Y - boxRef.MinPoint.Y) * 10)
                Dim Z_mm As Integer = Math.Round((boxRef.MaxPoint.Z - boxRef.MinPoint.Z) * 10)

                Dim stampText As String = "FOOTPRINT: " & L_mm & "mm (X) x " & W_mm & "mm (Y) x " & Z_mm & "mm (Z)"

                ' 2. Đẩy hệ số này vào Bộ nhớ tạm (Clipboard). 
                ' Sếp vào Fab.com nhấn Ctrl+V là nhả ra luông thông số chuyên nghiệp!
                My.Computer.Clipboard.SetText(stampText)
            Catch ex As Exception
            End Try

            ' =======================================================
            ' CHỤP ẢNH 4A, 4B, 4C: BỘ 3 ẢNH KHUNG DÂY (WIREFRAME) ĐỂ CHỐT SALE (CGTRADER BOOST)
            ' =======================================================
            oView.DisplayMode = DisplayModeEnum.kWireframeRendering
            oView.Update()

            ' WIREFRAME 1: ISOMETRIC TỔNG THỂ
            oCam.Perspective = True ' Đưa về hệ quy chiếu góc siêu tụ (Góc máy nguy hiểm)
            oCam.ViewOrientationType = ViewOrientationTypeEnum.kIsoTopRightViewOrientation
            oCam.Fit()
            oCam.GetExtents(camW, camH)
            oCam.SetExtents(camW * 0.75, camH * 0.75)
            oCam.Apply()
            oCam.SaveAsBitmap(savePath & "\" & baseName & "_04a_CAD_Wireframe_Proof.png", resWidth, resHeight)

                If CheckEscape() Then
                    ThisApplication.StatusBarText = "🛑 ĐÃ DỪNG TIẾN TRÌNH THEO LỆNH (GIỮ PHÍM ESC)!"
                    Exit Sub
                End If
                SafeYield(20)

            ' WIREFRAME 2: ORTHOGRAPHIC FRONT (GÓC CHIẾU THẲNG)
            oCam.Perspective = True ' Ép về trục giao
            oCam.ViewOrientationType = ViewOrientationTypeEnum.kFrontViewOrientation
            oCam.Fit()
            oCam.GetExtents(camW, camH)
            oCam.SetExtents(camW * 1.02, camH * 1.02)
            oCam.Apply()
            oCam.SaveAsBitmap(savePath & "\" & baseName & "_04b_CAD_Wireframe_Front.png", resWidth, resHeight)

                If CheckEscape() Then
                    ThisApplication.StatusBarText = "🛑 ĐÃ DỪNG TIẾN TRÌNH THEO LỆNH (GIỮ PHÍM ESC)!"
                    Exit Sub
                End If
                SafeYield(20)

            ' WIREFRAME 3: CLOSE-UP DETAIL (ĐẶC TẢ CHI TIẾT)
            oCam.Perspective = True ' Bật lại tụ góc cận cảnh
            oCam.ViewOrientationType = ViewOrientationTypeEnum.kIsoTopLeftViewOrientation
            oCam.Fit()
            oCam.GetExtents(camW, camH)
            oCam.SetExtents(camW * 0.50, camH * 0.50) ' Ép Zoom 50% bắt dính chi tiết
            oCam.Apply()
            oCam.SaveAsBitmap(savePath & "\" & baseName & "_04c_CAD_Wireframe_Detail.png", resWidth, resHeight)
        	If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 04D & 04E: GÓC 3/4 CHẾ ĐỘ VISIBLE EDGE (HIDDEN LINE REMOVED)
            ' kWireframeNoHiddenEdges — chỉ hiện viền ngoài, sạch sẽ, chuẩn B2B
            ' =======================================================
            oView.DisplayMode = DisplayModeEnum.kWireframeNoHiddenEdges
            oView.Update()
            ' 04D — Góc 3/4 Phải (IsoTopRight)
            oCam.Perspective = True
            oCam.ViewOrientationType = ViewOrientationTypeEnum.kIsoTopRightViewOrientation
            oCam.Fit()
            oCam.GetExtents(camW, camH)
            oCam.SetExtents(camW * 0.78, camH * 0.78)
            oCam.Apply()
            oCam.SaveAsBitmap(savePath & "\" & baseName & "_04d_VisibleEdge_3Q_Right.png", resWidth, resHeight)
        	If CheckEscape() Then
                    ThisApplication.StatusBarText = "🛑 ĐÃ DỪNG TIẾN TRÌNH THEO LỆNH (GIỮ PHÍM ESC)!"
                    Exit Sub
                End If
                SafeYield(20)
            ' 04E — Góc 3/4 Trái (IsoTopLeft)
            oCam.Perspective = True
            oCam.ViewOrientationType = ViewOrientationTypeEnum.kIsoTopLeftViewOrientation
            oCam.Fit()
            oCam.GetExtents(camW, camH)
            oCam.SetExtents(camW * 0.78, camH * 0.78)
            oCam.Apply()
            oCam.SaveAsBitmap(savePath & "\" & baseName & "_04e_VisibleEdge_3Q_Left.png", resWidth, resHeight)

                If CheckEscape() Then
                    ThisApplication.StatusBarText = "🛑 ĐÃ DỪNG TIẾN TRÌNH THEO LỆNH (GIỮ PHÍM ESC)!"
                    Exit Sub
                End If
                SafeYield(20)

            ' TRẢ LẠI SHADED WITH EDGES (CỐ ĐỊNH) ĐỂ CHỤP TIẾP CÁC ẢNH 05-10 CÓ VIỀN KỸ THUẬT
            ' KHÔNG dùng originalDisplayMode vì khi chạy Batch, nó bị cache sai thành kRealistic!
            oView.DisplayMode = DisplayModeEnum.kShadedWithEdgesRendering
            oView.Update()

            ' =======================================================
            ' CHỤP ẢNH 5, 6, 7: CÁC MẶT CHIẾU VUÔNG GÓC (ORTHOGRAPHIC)
            ' =======================================================
            oCam.Perspective = True

            oCam.ViewOrientationType = ViewOrientationTypeEnum.kFrontViewOrientation
            oCam.Fit()
            oCam.GetExtents(camW, camH)
            oCam.SetExtents(camW * 1.02, camH * 1.02)
            oCam.Apply()
            oCam.SaveAsBitmap(savePath & "\" & baseName & "_05_Front_Elevation.png", resWidth, resHeight)

                If CheckEscape() Then
                    ThisApplication.StatusBarText = "🛑 ĐÃ DỪNG TIẾN TRÌNH THEO LỆNH (GIỮ PHÍM ESC)!"
                    Exit Sub
                End If
                SafeYield(20)

            oCam.ViewOrientationType = ViewOrientationTypeEnum.kRightViewOrientation
            oCam.Fit()
            oCam.GetExtents(camW, camH)
            oCam.SetExtents(camW * 1.02, camH * 1.02)
            oCam.Apply()
            oCam.SaveAsBitmap(savePath & "\" & baseName & "_06_Right_Profile.png", resWidth, resHeight)

                If CheckEscape() Then
                    ThisApplication.StatusBarText = "🛑 ĐÃ DỪNG TIẾN TRÌNH THEO LỆNH (GIỮ PHÍM ESC)!"
                    Exit Sub
                End If
                SafeYield(20)

            oCam.ViewOrientationType = ViewOrientationTypeEnum.kLeftViewOrientation
            oCam.Fit()
            oCam.GetExtents(camW, camH)
            oCam.SetExtents(camW * 1.02, camH * 1.02)
            oCam.Apply()
            oCam.SaveAsBitmap(savePath & "\" & baseName & "_07_Left_Profile.png", resWidth, resHeight)

                If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 8, 9: GÓC ĐẶC TẢ - ZOOM CẬN CẢNH (CLOSE-UPS)
            ' =======================================================
            oCam.Perspective = True ' Bật lại tụ góc cho ngầu

            oCam.ViewOrientationType = ViewOrientationTypeEnum.kIsoTopRightViewOrientation
            oCam.Fit()
            oCam.GetExtents(camW, camH)
            oCam.SetExtents(camW * 0.55, camH * 0.55) ' Zoom thẳng vào 55%
            oCam.Apply()
            oCam.SaveAsBitmap(savePath & "\" & baseName & "_08_Detail_CloseUp_1.png", resWidth, resHeight)

                If CheckEscape() Then
                    ThisApplication.StatusBarText = "🛑 ĐÃ DỪNG TIẾN TRÌNH THEO LỆNH (GIỮ PHÍM ESC)!"
                    Exit Sub
                End If
                SafeYield(20)

            oCam.ViewOrientationType = ViewOrientationTypeEnum.kIsoTopLeftViewOrientation
            oCam.Fit()
            oCam.GetExtents(camW, camH)
            oCam.SetExtents(camW * 0.50, camH * 0.50) ' Ép Zoom 50% bắt dính mặt trước
            oCam.Apply()
            oCam.SaveAsBitmap(savePath & "\" & baseName & "_09_Detail_CloseUp_2.png", resWidth, resHeight)

                If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 10: MẶT LƯNG (REAR ELEVATION) ĐỂ ĐỦ BỘ BẢN VẼ
            ' =======================================================
            oCam.Perspective = True ' Ép về trục giao cho dễ đo đạc
            oCam.ViewOrientationType = ViewOrientationTypeEnum.kBackViewOrientation
            oCam.Fit()
            oCam.GetExtents(camW, camH)
            oCam.SetExtents(camW * 1.02, camH * 1.02)
            oCam.Apply()
            oCam.SaveAsBitmap(savePath & "\" & baseName & "_10_Rear_Elevation.png", resWidth, resHeight)

                If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 11: MẶT ĐÁY (BOTTOM VIEW) — ĐỂ THẤY CHÂN MÁY, CẤU TRÚC ĐÁY
            ' =======================================================
            oCam.Perspective = True
            oCam.ViewOrientationType = ViewOrientationTypeEnum.kBottomViewOrientation
            oCam.Fit()
            oCam.GetExtents(camW, camH)
            oCam.SetExtents(camW * 1.02, camH * 1.02)
            oCam.Apply()
            oCam.SaveAsBitmap(savePath & "\" & baseName & "_11_Bottom_View.png", resWidth, resHeight)

                If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 12: ISO GÓC DƯỚI TRÁI (CUSTOM CAMERA - SAFE)
            ' Dùng toán học Eye/Target thay vì Enum không tồn tại trong Inventor
            ' =======================================================
            Try
                If rBox IsNot Nothing Then
                    Dim tg12 As TransientGeometry = ThisApplication.TransientGeometry
                    Dim cx12 As Double = (rBox.MinPoint.X + rBox.MaxPoint.X) / 2
                    Dim cy12 As Double = (rBox.MinPoint.Y + rBox.MaxPoint.Y) / 2
                    Dim cz12 As Double = (rBox.MinPoint.Z + rBox.MaxPoint.Z) / 2
                    Dim mD12 As Double = Math.Max(rBox.MaxPoint.X - rBox.MinPoint.X, Math.Max(rBox.MaxPoint.Y - rBox.MinPoint.Y, rBox.MaxPoint.Z - rBox.MinPoint.Z))
                    ' Góc nhìn từ dưới-trái (X-, Z+, Y thấp)
                    oCam.Perspective = True
                    oCam.Eye = tg12.CreatePoint(cx12 - mD12 * 1.2, cy12 - mD12 * 0.3, cz12 + mD12 * 1.2)
                    oCam.Target = tg12.CreatePoint(cx12, cy12, cz12)
                    oCam.UpVector = tg12.CreateUnitVector(0, 1, 0)
                    oCam.GetExtents(camW, camH)
                    oCam.SetExtents(camW * 0.80, camH * 0.80)
                    oCam.Apply()
                    oCam.SaveAsBitmap(savePath & "\" & baseName & "_12_ISO_BottomLeft.png", resWidth, resHeight)

                If CheckEscape() Then
                    ThisApplication.StatusBarText = "🛑 ĐÃ DỪNG TIẾN TRÌNH THEO LỆNH (GIỮ PHÍM ESC)!"
                    Exit Sub
                End If
                SafeYield(20)
                End If
            Catch : End Try

            ' =======================================================
            ' CHỤP ẢNH 13: EXTREME CLOSE-UP (ZOOM 35%) — KHOE ĐỘ CHI TIẾT VẬT LÝ
            ' =======================================================
            oCam.Perspective = True
            oCam.ViewOrientationType = ViewOrientationTypeEnum.kIsoTopRightViewOrientation
            oCam.Fit()
            oCam.GetExtents(camW, camH)
            oCam.SetExtents(camW * 0.45, camH * 0.45) ' Zoom 55% an toàn - không xuyên model
            oCam.Apply()
            oCam.SaveAsBitmap(savePath & "\" & baseName & "_13_Extreme_CloseUp.png", resWidth, resHeight)

                If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 14: WIREFRAME MẶT BẰNG TOP (4th WIREFRAME)
            ' =======================================================
            oView.DisplayMode = DisplayModeEnum.kWireframeRendering
            oView.Update()
            oCam.Perspective = True
            oCam.ViewOrientationType = ViewOrientationTypeEnum.kTopViewOrientation
            oCam.Fit()
            oCam.GetExtents(camW, camH)
            oCam.SetExtents(camW * 1.05, camH * 1.05)
            oCam.Apply()
            oCam.SaveAsBitmap(savePath & "\" & baseName & "_14_Wireframe_TopPlan.png", resWidth, resHeight)

                If CheckEscape() Then
                    ThisApplication.StatusBarText = "🛑 ĐÃ DỪNG TIẾN TRÌNH THEO LỆNH (GIỮ PHÍM ESC)!"
                    Exit Sub
                End If
                SafeYield(20)
            ' Trả lại màu chuẩn
            oView.DisplayMode = DisplayModeEnum.kShadedWithEdgesRendering
            oView.Update()

            ' =======================================================
            ' CHỤP ẢNH 15: ISO GÓC DƯỚI PHẢI (CUSTOM CAMERA - SAFE)
            ' Dùng toán học Eye/Target thay vì Enum không tồn tại trong Inventor
            ' =======================================================
            Try
                If rBox IsNot Nothing Then
                    Dim tg15 As TransientGeometry = ThisApplication.TransientGeometry
                    Dim cx15 As Double = (rBox.MinPoint.X + rBox.MaxPoint.X) / 2
                    Dim cy15 As Double = (rBox.MinPoint.Y + rBox.MaxPoint.Y) / 2
                    Dim cz15 As Double = (rBox.MinPoint.Z + rBox.MaxPoint.Z) / 2
                    Dim mD15 As Double = Math.Max(rBox.MaxPoint.X - rBox.MinPoint.X, Math.Max(rBox.MaxPoint.Y - rBox.MinPoint.Y, rBox.MaxPoint.Z - rBox.MinPoint.Z))
                    ' Góc nhìn từ dưới-phải (X+, Z+, Y thấp)
                    oCam.Perspective = True
                    oCam.Eye = tg15.CreatePoint(cx15 + mD15 * 1.2, cy15 - mD15 * 0.3, cz15 + mD15 * 1.2)
                    oCam.Target = tg15.CreatePoint(cx15, cy15, cz15)
                    oCam.UpVector = tg15.CreateUnitVector(0, 1, 0)
                    oCam.GetExtents(camW, camH)
                    oCam.SetExtents(camW * 0.80, camH * 0.80)
                    oCam.Apply()
                    oCam.SaveAsBitmap(savePath & "\" & baseName & "_15_ISO_BottomRight.png", resWidth, resHeight)

                If CheckEscape() Then
                    ThisApplication.StatusBarText = "🛑 ĐÃ DỪNG TIẾN TRÌNH THEO LỆNH (GIỮ PHÍM ESC)!"
                    Exit Sub
                End If
                SafeYield(20)
                End If
            Catch : End Try

            ' =======================================================
            ' CHỤP ẢNH 16-20: BỘ REALISTIC PERSPECTIVE (KHÔNG CÓ VIỀN - THUẦN BỀ MẶT VẬT LÝ)
            ' Mục đích: Đa dạng hóa thư viện ảnh, tăng điểm CGTrader Publishing Score
            ' =======================================================
            oView.DisplayMode = DisplayModeEnum.kRealisticRendering
            oView.Update()

            ' REALISTIC 1 - ISO TỔNG THỂ (FULL VIEW)
            oCam.Perspective = True
            oCam.ViewOrientationType = ViewOrientationTypeEnum.kIsoTopRightViewOrientation
            oCam.Fit()
            oCam.GetExtents(camW, camH)
            oCam.SetExtents(camW * 0.75, camH * 0.75)
            oCam.Apply()
            oCam.SaveAsBitmap(savePath & "\" & baseName & "_16_Realistic_ISO_Overview.png", resWidth, resHeight)

                If CheckEscape() Then
                    ThisApplication.StatusBarText = "🛑 ĐÃ DỪNG TIẾN TRÌNH THEO LỆNH (GIỮ PHÍM ESC)!"
                    Exit Sub
                End If
                SafeYield(20)

            ' REALISTIC 2 - ISO TRÁI (PIPING VIEW)
            oCam.ViewOrientationType = ViewOrientationTypeEnum.kIsoTopLeftViewOrientation
            oCam.Fit()
            oCam.GetExtents(camW, camH)
            oCam.SetExtents(camW * 0.75, camH * 0.75)
            oCam.Apply()
            oCam.SaveAsBitmap(savePath & "\" & baseName & "_17_Realistic_ISO_Left.png", resWidth, resHeight)

                If CheckEscape() Then
                    ThisApplication.StatusBarText = "🛑 ĐÃ DỪNG TIẾN TRÌNH THEO LỆNH (GIỮ PHÍM ESC)!"
                    Exit Sub
                End If
                SafeYield(20)

            ' REALISTIC 3 - FRONT ELEVATION (MẶT TIỀN PHẲNG LÌ)
            oCam.Perspective = True
            oCam.ViewOrientationType = ViewOrientationTypeEnum.kFrontViewOrientation
            oCam.Fit()
            oCam.GetExtents(camW, camH)
            oCam.SetExtents(camW * 1.02, camH * 1.02)
            oCam.Apply()
            oCam.SaveAsBitmap(savePath & "\" & baseName & "_18_Realistic_Front_Elev.png", resWidth, resHeight)

                If CheckEscape() Then
                    ThisApplication.StatusBarText = "🛑 ĐÃ DỪNG TIẾN TRÌNH THEO LỆNH (GIỮ PHÍM ESC)!"
                    Exit Sub
                End If
                SafeYield(20)

            ' REALISTIC 4 - CLOSE-UP CHI TIẾT (PHỐI CẢNH CẬN BỀ MẶT)
            oCam.Perspective = True
            oCam.ViewOrientationType = ViewOrientationTypeEnum.kIsoTopRightViewOrientation
            oCam.Fit()
            oCam.GetExtents(camW, camH)
            oCam.SetExtents(camW * 0.45, camH * 0.45)
            oCam.Apply()
            oCam.SaveAsBitmap(savePath & "\" & baseName & "_19_Realistic_CloseUp.png", resWidth, resHeight)

                If CheckEscape() Then
                    ThisApplication.StatusBarText = "🛑 ĐÃ DỪNG TIẾN TRÌNH THEO LỆNH (GIỮ PHÍM ESC)!"
                    Exit Sub
                End If
                SafeYield(20)

            ' REALISTIC 5 - LOW ANGLE HERO (GÓC MÁY ĐẤT)
            Try
                If rBox IsNot Nothing Then
                    Dim tgR As TransientGeometry = ThisApplication.TransientGeometry
                    Dim cxR As Double = (rBox.MinPoint.X + rBox.MaxPoint.X) / 2
                    Dim cyR As Double = (rBox.MinPoint.Y + rBox.MaxPoint.Y) / 2
                    Dim czR As Double = (rBox.MinPoint.Z + rBox.MaxPoint.Z) / 2
                    Dim mHR As Double = rBox.MaxPoint.Y - rBox.MinPoint.Y
                    Dim mWR As Double = Math.Max(rBox.MaxPoint.X - rBox.MinPoint.X, rBox.MaxPoint.Z - rBox.MinPoint.Z)
                    oCam.Perspective = True
                    oCam.Eye = tgR.CreatePoint(cxR + mWR * 0.9, rBox.MinPoint.Y - mHR * 0.1, czR + mWR * 1.1)
                    oCam.Target = tgR.CreatePoint(cxR, rBox.MaxPoint.Y * 0.85, czR)
                    oCam.UpVector = tgR.CreateUnitVector(0, 1, 0)
                    oCam.GetExtents(camW, camH)
                    oCam.SetExtents(camW * 0.80, camH * 0.80)
                    oCam.Apply()
                    oCam.SaveAsBitmap(savePath & "\" & baseName & "_20_Realistic_LowAngle.png", resWidth, resHeight)

                If CheckEscape() Then
                    ThisApplication.StatusBarText = "🛑 ĐÃ DỪNG TIẾN TRÌNH THEO LỆNH (GIỮ PHÍM ESC)!"
                    Exit Sub
                End If
                SafeYield(20)
                End If
            Catch : End Try

            ' =======================================================
            ' CHỤP ẢNH 21-23: BỘ ẢNH 3/4 MICRO CLOSE-UP (CẬN CẢNH SIÊU NÉT PHỐI CẢNH 3/4)
            ' Mục đích: Tối ưu điểm CGTrader Publishing Score, khoe chi tiết ren ốc/mặt bích/van
            ' =======================================================
            oView.DisplayMode = DisplayModeEnum.kShadedWithEdgesRendering
            oView.Update()

            ' 21. MICRO 3/4 PHẢI (VALVE HEADER & PIPING THREADS)
            oCam.Perspective = True
            oCam.ViewOrientationType = ViewOrientationTypeEnum.kIsoTopRightViewOrientation
            oCam.Fit()
            oCam.GetExtents(camW, camH)
            oCam.SetExtents(camW * 0.35, camH * 0.35) ' Ép Zoom cận cảnh 35%
            oCam.Apply()
            oCam.SaveAsBitmap(savePath & "\" & baseName & "_21_Micro_3Q_Valve_Header.png", resWidth, resHeight)
            If CheckEscape() Then
                    ThisApplication.StatusBarText = "🛑 ĐÃ DỪNG TIẾN TRÌNH THEO LỆNH (GIỮ PHÍM ESC)!"
                    Exit Sub
                End If
                SafeYield(20)

            ' 22. MICRO 3/4 TRÁI (PUMP MANIFOLD & GAUGES)
            oCam.Perspective = True
            oCam.ViewOrientationType = ViewOrientationTypeEnum.kIsoTopLeftViewOrientation
            oCam.Fit()
            oCam.GetExtents(camW, camH)
            oCam.SetExtents(camW * 0.35, camH * 0.35)
            oCam.Apply()
            oCam.SaveAsBitmap(savePath & "\" & baseName & "_22_Micro_3Q_Pump_Manifold.png", resWidth, resHeight)
            If CheckEscape() Then
                    ThisApplication.StatusBarText = "🛑 ĐÃ DỪNG TIẾN TRÌNH THEO LỆNH (GIỮ PHÍM ESC)!"
                    Exit Sub
                End If
                SafeYield(20)

            ' 23. MICRO 3/4 WIREFRAME TECHNICAL (VISIBLE EDGE)
            oView.DisplayMode = DisplayModeEnum.kWireframeNoHiddenEdges
            oView.Update()
            oCam.Perspective = True
            oCam.ViewOrientationType = ViewOrientationTypeEnum.kIsoTopRightViewOrientation
            oCam.Fit()
            oCam.GetExtents(camW, camH)
            oCam.SetExtents(camW * 0.35, camH * 0.35)
            oCam.Apply()
            oCam.SaveAsBitmap(savePath & "\" & baseName & "_23_Micro_3Q_Wireframe_Detail.png", resWidth, resHeight)
            If CheckEscape() Then
                    ThisApplication.StatusBarText = "🛑 ĐÃ DỪNG TIẾN TRÌNH THEO LỆNH (GIỮ PHÍM ESC)!"
                    Exit Sub
                End If
                SafeYield(20)

            ' TRẢ LẠI SHADED WITH EDGES SAU KHI CHỤP XONG BỘ REALISTIC & MICRO
            oView.DisplayMode = DisplayModeEnum.kShadedWithEdgesRendering
            oView.Update()

            ' =======================================================
            ' BURN WATERMARK DIMENSIONS & COPYRIGHT OVERLAY TỔNG LỰC
            ' =======================================================
            Try
                ' Toàn bộ cấu hình Bản quyền được nhúng chuẩn trực tiếp bên trong vòng lặp Graphic để tránh trùng lặp biến.

                Dim pngFiles As String() = System.IO.Directory.GetFiles(savePath, "*.png")
                For Each imgFile As String In pngFiles
                    If CheckEscape() Then
                        ThisApplication.StatusBarText = "🛑 ĐÃ DỪNG VÒNG LẶP THEO LỆNH (GIỮ PHÍM ESC)!"
                        Exit Sub
                    End If
                    SafeYield(10)
                    If imgFile.Contains("temp_") Then Continue For

                    ' Lưới lọc Cực Đoan: Tránh dập 2 lần hoặc dập đè sang rác không gian của Bản vẽ CAD (_GA_, _Drawing_)
                    If imgFile.Contains("_GA_") OrElse imgFile.Contains("_Drawing_") Then Continue For

                    Dim tempImgPath As String = savePath & "\temp_" & System.IO.Path.GetFileName(imgFile)
                    Dim isHero As Boolean = imgFile.Contains("_01_Overall_Hero")

                    Using bmp As New System.Drawing.Bitmap(imgFile)
                        Using g As System.Drawing.Graphics = System.Drawing.Graphics.FromImage(bmp)
                            g.SmoothingMode = System.Drawing.Drawing2D.SmoothingMode.AntiAlias

                            ' 1. DIMENSION WATERMARK (Chỉ xuất trên bức Số 1 - Hero Thumbnail)
                            If isHero AndAlso sizeLabel <> "" Then
                                Dim dims As String() = sizeLabel.Split("|")
                                Dim dimTitle As String = "OVERALL FOOTPRINT"
                                Dim dimVals As String = String.Format("L: {0} x W: {1} x H: {2} mm", dims(0), dims(1), dims(2))

                                Using titleFont As New System.Drawing.Font("Arial Narrow", 40, System.Drawing.FontStyle.Bold)
                                Using valFont As New System.Drawing.Font("Arial Narrow", 52, System.Drawing.FontStyle.Bold)
                                    Dim tSz As System.Drawing.SizeF = g.MeasureString(dimTitle, titleFont)
                                    Dim vSz As System.Drawing.SizeF = g.MeasureString(dimVals, valFont)

                                    Dim wBox As Single = Math.Max(tSz.Width, vSz.Width)
                                    Dim padding As Single = 35
                                    Dim boxH As Single = tSz.Height + vSz.Height + 10

                                    ' Tọa góc Dưới Cùng Bên Trái (Bottom-Left)
                                    Dim boxX As Single = 100
                                    Dim boxY As Single = bmp.Height - boxH - 100 - padding*2

                                    Using bgBrush As New System.Drawing.SolidBrush(System.Drawing.Color.FromArgb(200, 20, 20, 20))
                                        g.FillRectangle(bgBrush, boxX, boxY, wBox + padding*2, boxH + padding*2)
                                    End Using
                                    Using borderPen As New System.Drawing.Pen(System.Drawing.Color.FromArgb(255, 140, 0), 4)
                                        g.DrawRectangle(borderPen, boxX, boxY, wBox + padding*2, boxH + padding*2)
                                    End Using
                                    Using tBrush As New System.Drawing.SolidBrush(System.Drawing.Color.White)
                                        g.DrawString(dimTitle, titleFont, tBrush, boxX + padding, boxY + padding)
                                    End Using
                                    Using vBrush As New System.Drawing.SolidBrush(System.Drawing.Color.FromArgb(255, 200, 50))
                                        g.DrawString(dimVals, valFont, vBrush, boxX + padding, boxY + padding + tSz.Height + 10)
                                    End Using
                                End Using
                                End Using
                            End If

                            ' ------------------------------------------------------------------
                            ' LỚP 1: LÁ CỜ VIỆT NAM (GÓC TRÊN BÊN TRÁI)
                            ' ------------------------------------------------------------------
                            Dim isVertical As Boolean = (bmp.Height > bmp.Width)
                            Dim flagW As Single = bmp.Width * (If(isVertical, 0.140F, 0.105F))
                            Dim flagH As Single = flagW * 0.6667F
                            Dim flagX As Single = bmp.Width * (If(isVertical, 0.045F, 0.030F))
                            Dim flagY As Single = bmp.Height * 0.030F
                            Dim flagPath As String = masterDir & "\Z_Tools\vietnam_flag.png"
                            If System.IO.File.Exists(flagPath) Then
                                Try
                                    Dim flagBytes As Byte() = System.IO.File.ReadAllBytes(flagPath)
                                    Using flagMs As New System.IO.MemoryStream(flagBytes)
                                        Using flagImg As New System.Drawing.Bitmap(flagMs)
                                            g.DrawImage(flagImg, flagX, flagY, flagW, flagH)
                                        End Using
                                    End Using
                                Catch : End Try
                            End If

                            ' ------------------------------------------------------------------
                            ' LỚP 2: BẢN QUYỀN THỦY TINH CHÍNH GIỮA MÀN HÌNH (@tanphan1105)
                            ' ------------------------------------------------------------------
                            Dim mailY As Single = bmp.Height * (If(isVertical, 0.43F, 0.44F))
                            g.TranslateTransform(bmp.Width / 2.0F, mailY)
                            Dim mailText As String = "@tanphan1105"
                            Dim mailSize As Single = bmp.Width * (If(isVertical, 0.082F, 0.052F))
                            Using mailFont As New System.Drawing.Font("Arial Black", mailSize, System.Drawing.FontStyle.Bold)
                                Using gp2 As New System.Drawing.Drawing2D.GraphicsPath()
                                    Dim sf2 As New System.Drawing.StringFormat() 
                                    sf2.Alignment = System.Drawing.StringAlignment.Center
                                    sf2.LineAlignment = System.Drawing.StringAlignment.Center
                                    gp2.AddString(mailText, mailFont.FontFamily, CInt(mailFont.Style), mailFont.Size, New System.Drawing.PointF(0, 0), sf2)
                                    Dim pThick2 As Single = Math.Max(1.0F, bmp.Width * 0.0015F)
                                    Using darkPen2 As New System.Drawing.Pen(System.Drawing.Color.FromArgb(35, 0, 0, 0), pThick2)
                                        g.TranslateTransform(pThick2, pThick2)
                                        g.DrawPath(darkPen2, gp2)
                                        g.TranslateTransform(-pThick2, -pThick2)
                                    End Using
                                    Using glassBrush As New System.Drawing.SolidBrush(System.Drawing.Color.FromArgb(10, 255, 255, 255))
                                        g.FillPath(glassBrush, gp2)
                                    End Using
                                    Using lightPen2 As New System.Drawing.Pen(System.Drawing.Color.FromArgb(55, 255, 255, 255), pThick2)
                                        g.TranslateTransform(-pThick2, -pThick2)
                                        g.DrawPath(lightPen2, gp2)
                                        g.TranslateTransform(pThick2, pThick2)
                                    End Using
                                End Using
                            End Using

                            g.ResetTransform()

                            ' ------------------------------------------------------------------
                            ' LỚP 3: THẺ GREEN CARD LOGO DIAGONAL GRADIENT HIGH CONTRAST
                            ' ------------------------------------------------------------------
                            Dim brandText As String = "WaterTreatment3D"
                            Dim contactText As String = "@tanphan1105 | Zalo: +84985267326"

                            Dim brandSize As Single = bmp.Width * (If(isVertical, 0.022F, 0.013F))
                            Dim contactSize As Single = bmp.Width * (If(isVertical, 0.026F, 0.015F))

                            Using brandFont As New System.Drawing.Font("Arial", brandSize, System.Drawing.FontStyle.Bold)
                            Using contactFont As New System.Drawing.Font("Arial", contactSize, System.Drawing.FontStyle.Bold)
                                Dim brandSz As System.Drawing.SizeF = g.MeasureString(brandText, brandFont)
                                Dim contactSz As System.Drawing.SizeF = g.MeasureString(contactText, contactFont)

                                Dim maxW As Single = Math.Max(brandSz.Width, contactSz.Width)
                                Dim qrSize As Single = bmp.Width * (If(isVertical, 0.145F, 0.075F))
                                Dim cPad As Single = bmp.Width * (If(isVertical, 0.022F, 0.010F))
                                Dim gap As Single = bmp.Width * (If(isVertical, 0.022F, 0.014F))

                                ' LOAD QR CODE SAFE VIA MEMORYSTREAM
                                Dim hasQR As Boolean = False
                                Dim qrPath As String = masterDir & "\Z_Tools\wt3d_qr_green.png"
                                Dim qrBmp As System.Drawing.Bitmap = Nothing
                                If System.IO.File.Exists(qrPath) Then
                                    Try
                                        Dim qrBytes As Byte() = System.IO.File.ReadAllBytes(qrPath)
                                        Dim qrMs As New System.IO.MemoryStream(qrBytes)
                                        qrBmp = New System.Drawing.Bitmap(qrMs)
                                        hasQR = True
                                    Catch : End Try
                                End If

                                Dim effQRSize As Single = If(hasQR, qrSize, 0.0F)
                                Dim effGap As Single = If(hasQR, gap, 0.0F)

                                Dim totalW As Single = maxW + effGap + effQRSize
                                Dim textBlockH As Single = brandSz.Height + contactSz.Height + (bmp.Height * If(isVertical, 0.012F, 0.008F))
                                Dim totalH As Single = Math.Max(textBlockH, qrSize)

                                Dim cardX As Single
                                Dim cardY As Single
                                If isVertical Then
                                    cardX = (bmp.Width - (totalW + cPad*2)) / 2.0F
                                    cardY = bmp.Height - totalH - (bmp.Height * 0.035F) - cPad*2
                                Else
                                    cardX = bmp.Width - totalW - (bmp.Width * 0.025F) - cPad*2
                                    cardY = bmp.Height - totalH - (bmp.Height * 0.035F) - cPad*2
                                End If

                                ' DRAW ROUNDED RECTANGLE GRADIENT CARD
                                Dim rectW As Single = totalW + cPad*2
                                Dim rectH As Single = totalH + cPad*2
                                Dim rRadius As Single = Math.Max(6.0F, bmp.Width * 0.008F)
                                Using cardPath As New System.Drawing.Drawing2D.GraphicsPath()
                                    cardPath.AddArc(cardX, cardY, rRadius, rRadius, 180, 90)
                                    cardPath.AddArc(cardX + rectW - rRadius, cardY, rRadius, rRadius, 270, 90)
                                    cardPath.AddArc(cardX + rectW - rRadius, cardY + rectH - rRadius, rRadius, rRadius, 0, 90)
                                    cardPath.AddArc(cardX, cardY + rectH - rRadius, rRadius, rRadius, 90, 90)
                                    cardPath.CloseAllFigures()

                                    Dim rectF As New System.Drawing.RectangleF(cardX, cardY, rectW, rectH)
                                    Dim col1 As System.Drawing.Color = System.Drawing.Color.FromArgb(225, 52, 199, 89)
                                    Dim col2 As System.Drawing.Color = System.Drawing.Color.FromArgb(220, 24, 150, 68)
                                    Using gradBrush As New System.Drawing.Drawing2D.LinearGradientBrush(rectF, col1, col2, 45.0F)
                                        g.FillPath(gradBrush, cardPath)
                                    End Using
                                    Using borderPen As New System.Drawing.Pen(System.Drawing.Color.FromArgb(240, 255, 255, 255), 1.0F)
                                        g.DrawPath(borderPen, cardPath)
                                    End Using
                                End Using

                                Dim currY As Single = cardY + cPad + (totalH - textBlockH) / 2.0F

                                ' DRAW BRAND TEXT & SHADOW
                                Using shadowBrush As New System.Drawing.SolidBrush(System.Drawing.Color.FromArgb(110, 10, 40, 15))
                                    g.DrawString(brandText, brandFont, shadowBrush, cardX + cPad + 3, currY + 3)
                                End Using
                                Using mainBrush As New System.Drawing.SolidBrush(System.Drawing.Color.FromArgb(255, 255, 255, 255))
                                    g.DrawString(brandText, brandFont, mainBrush, cardX + cPad, currY)
                                End Using

                                currY += brandSz.Height + (bmp.Height * 0.004F)

                                ' DRAW CONTACT TEXT & SHADOW
                                Using shadowBrush As New System.Drawing.SolidBrush(System.Drawing.Color.FromArgb(110, 10, 40, 15))
                                    g.DrawString(contactText, contactFont, shadowBrush, cardX + cPad + 3, currY + 3)
                                End Using
                                Using mainBrush As New System.Drawing.SolidBrush(System.Drawing.Color.FromArgb(255, 255, 255, 255))
                                    g.DrawString(contactText, contactFont, mainBrush, cardX + cPad, currY)
                                End Using

                                If hasQR AndAlso qrBmp IsNot Nothing Then
                                    Try
                                        Dim qrX As Single = cardX + cPad + maxW + gap
                                        Dim qrY As Single = cardY + cPad + (totalH - qrSize)/2.0F
                                        Using qrBgPen As New System.Drawing.SolidBrush(System.Drawing.Color.FromArgb(255, 255, 255, 255))
                                            g.FillRectangle(qrBgPen, qrX - 4, qrY - 4, qrSize + 8, qrSize + 8)
                                        End Using
                                        g.DrawImage(qrBmp, qrX, qrY, qrSize, qrSize)
                                        qrBmp.Dispose()
                                    Catch : End Try
                                End If
                            End Using
                            End Using
                        End Using
                        bmp.Save(tempImgPath, System.Drawing.Imaging.ImageFormat.Png)
                    End Using

                    System.IO.File.Delete(imgFile)
                    System.IO.File.Move(tempImgPath, imgFile)
                Next
            Catch ex As Exception
                ' Lỗi đồ họa thì bỏ lơ
            End Try

            ' Tự động mở thư mục chứa ảnh vừa chụp xong
            Try : System.Diagnostics.Process.Start("explorer.exe", savePath) : Catch : End Try

        Catch ex As Exception
        End Try
    End Sub
End Class
