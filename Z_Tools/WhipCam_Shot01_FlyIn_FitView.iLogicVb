AddReference "System.Drawing"
AddReference "System.Windows.Forms"

' ==============================================================================
' WT3D WHIPCAM STUDIO — DIRECTOR MULTI-SHOT MASTER (TABBED BENTO)
' (Full Multi-Shot Studio: Shot 01, Shot 02, Shot 03, Shot 04 & Master Timeline)
' Lead Engineer & System Architect: Phan Trong Tan (@tanphan1105)
' ==============================================================================
Imports System
Imports System.Collections.Generic
Imports System.IO
Imports System.Drawing
Imports System.Windows.Forms
Imports System.Runtime.InteropServices
Imports Inventor

Public Class ThisRule

    ' Trap phím ESC để dừng khẩn cấp (Điều lệ 17)
    Private Declare Function GetAsyncKeyState Lib "user32" (ByVal vKey As Integer) As Short
    Private Const VK_ESCAPE As Integer = &H1B

    Public Function CheckEscapeKey() As Boolean
        Return (GetAsyncKeyState(VK_ESCAPE) And &H8000) <> 0
    End Function

    Public Sub SafeYield(Optional ByVal sleepMs As Integer = 2)
        Try
            System.Windows.Forms.Application.DoEvents()
            If sleepMs > 0 Then System.Threading.Thread.Sleep(sleepMs)
        Catch
        End Try
    End Sub

    Public Sub CaptureVideoFrame(ByVal oCam As Inventor.Camera, ByVal exportCtx As VideoExportContext, ByVal oApp As Inventor.Application)
        If exportCtx Is Nothing OrElse Not exportCtx.IsExporting Then Return
        Try
            Dim frameFile As String = System.IO.Path.Combine(exportCtx.FrameFolder, "frame_" & exportCtx.FrameCounter.ToString("D5") & ".png")
            oCam.SaveAsBitmap(frameFile, exportCtx.ExportWidth, exportCtx.ExportHeight)
            exportCtx.FrameCounter += 1
            oApp.StatusBarText = "🎬 WT3D Video Render: [" & exportCtx.CurrentShotName & "] Khung hình " & (exportCtx.FrameCounter - 1).ToString() & " (Giữ ESC để dừng)..."
        Catch ex As Exception
        End Try
    End Sub

    ' --------------------------------------------------------------------------
    ' 1. 3D VECTOR MATH
    ' --------------------------------------------------------------------------
    Public Class Vec3
        Public X As Double
        Public Y As Double
        Public Z As Double

        Public Sub New()
            X = 0.0 : Y = 0.0 : Z = 0.0
        End Sub

        Public Sub New(ByVal _x As Double, ByVal _y As Double, ByVal _z As Double)
            X = _x : Y = _y : Z = _z
        End Sub

        Public Shared Operator +(ByVal a As Vec3, ByVal b As Vec3) As Vec3
            Return New Vec3(a.X + b.X, a.Y + b.Y, a.Z + b.Z)
        End Operator

        Public Shared Operator -(ByVal a As Vec3, ByVal b As Vec3) As Vec3
            Return New Vec3(a.X - b.X, a.Y - b.Y, a.Z - b.Z)
        End Operator

        Public Shared Operator *(ByVal a As Vec3, ByVal s As Double) As Vec3
            Return New Vec3(a.X * s, a.Y * s, a.Z * s)
        End Operator

        Public Shared Operator *(ByVal s As Double, ByVal a As Vec3) As Vec3
            Return New Vec3(a.X * s, a.Y * s, a.Z * s)
        End Operator

        Public Shared Operator /(ByVal a As Vec3, ByVal s As Double) As Vec3
            If Math.Abs(s) < 1E-12 Then Return New Vec3(0, 0, 0)
            Return New Vec3(a.X / s, a.Y / s, a.Z / s)
        End Operator

        Public Function Length() As Double
            Return Math.Sqrt(X * X + Y * Y + Z * Z)
        End Function

        Public Function Normalize() As Vec3
            Dim l As Double = Length()
            If l < 1E-12 Then Return New Vec3(0, 1, 0)
            Return New Vec3(X / l, Y / l, Z / l)
        End Function

        Public Function Dot(ByVal b As Vec3) As Double
            Return X * b.X + Y * b.Y + Z * b.Z
        End Function

        Public Function Cross(ByVal b As Vec3) As Vec3
            Return New Vec3(Y * b.Z - Z * b.Y, Z * b.X - X * b.Z, X * b.Y - Y * b.X)
        End Function

        Public Shared Function Distance(ByVal a As Vec3, ByVal b As Vec3) As Double
            Return (a - b).Length()
        End Function

        Public Shared Function Lerp(ByVal a As Vec3, ByVal b As Vec3, ByVal t As Double) As Vec3
            t = Math.Max(0.0, Math.Min(1.0, t))
            Return a + (b - a) * t
        End Function
    End Class

    ' --------------------------------------------------------------------------
    ' 2. THÔNG TIN MÔ HÌNH & HERO TARGETS
    ' --------------------------------------------------------------------------
    Public Class ModelInfo
        Public Center As Vec3
        Public MinPt As Vec3
        Public MaxPt As Vec3
        Public U As Vec3
        Public V As Vec3
        Public W As Vec3
        Public RU As Double
        Public RV As Double
        Public RH As Double
        Public Diag As Double
    End Class

    Public Class HeroTarget
        Public Name As String
        Public Center As Vec3
        Public Radius As Double
        Public Found As Boolean
    End Class

    ' --------------------------------------------------------------------------
    ' 3. CÁC LỚP CÀI ĐẶT THÔNG SỐ CHO TỪNG SHOT
    ' --------------------------------------------------------------------------
    Public Class Shot01Settings
        Public DurationSeconds As Double = 2.0
        Public FPS As Integer = 30
        Public Width As Integer = 1920
        Public Height As Integer = 1080
        Public RunMode As String = "PREVIEW"

        Public CornerMode As String = "BACK_LEFT"
        Public ViewAngleMode As String = "34_BOTTOM"

        Public SpeedMultiplier As Double = 2.00
        Public StartDistanceScale As Double = 7.00
        Public EndDistanceScale As Double = 0.30
        Public SwoopCurvature As Double = 10.00
        Public FOVStart As Double = 50.0
        Public FOVEnd As Double = 50.0
        Public BankStart As Double = 0.0
        Public BankEnd As Double = 0.0

        Public HoldSeconds As Double = 1.0
        Public EnableFlyOut As Boolean = False
        Public FlyOutDuration As Double = 2.0
    End Class

    Public Class Shot02Settings
    Public DurationSeconds As Double = 3.0
    Public FPS As Integer = 30
    Public RunMode As String = "PREVIEW"

    ' Góc 3/4 Đầu và Cuối
    Public CornerStart As String = "AUTO_C1"
    Public CornerEnd As String = "FRONT_LEFT"
    Public ViewAngleModeEnd As String = "34_BOTTOM"

    ' Kiểu bay: CURVED (Bay cong) hoặc STRAIGHT (Bay thẳng)
    Public TrajectoryMode As String = "CURVED"
    Public SwoopCurvature As Double = 10.00

    ' Kiểu gia tốc tốc độ: EASE_OUT (Chậm dần), EASE_IN (Nhanh dần), EASE_IN_OUT (Mượt 2 đầu), LINEAR (Đều)
    Public EasingMode As String = "EASE_IN"

    Public StartDistanceScale As Double = 0.30
    Public EndDistanceScale As Double = 0.70

    Public SpeedMultiplier As Double = 3.00
    Public FOVStart As Double = 50.0
    Public FOVEnd As Double = 50.0
    Public BankStart As Double = 30.0
    Public BankEnd As Double = 0.0

    Public HoldSeconds As Double = 0.0
End Class

    Public Class Shot03Settings
        Public DurationSeconds As Double = 4.0
        Public FPS As Integer = 30
        Public RunMode As String = "PREVIEW"

        ' 1. Tiêu điểm & Phân vùng con lắc
        Public FocusMode As String = "FRONT_FACADE" ' "FRONT_FACADE", "CORNER_1", "CORNER_2", "BACK_FACADE", "SKID_CENTER", "CUSTOM_PICK"
        Public CustomPickPoint As Vec3 = Nothing

        ' 2. Hướng góc & Cao độ
        Public CornerStart As String = "AUTO_C2"
        Public ViewAngleMode As String = "34_TOP" ' "34_BOTTOM", "34_LEVEL", "34_TOP" [Mặc định: 3/4 TRÊN]

        ' 3. Đong đưa con lắc (Pendulum Sway)
        Public SwayPercent As Double = 80.0       ' Độ đong đưa 80% theo chuẩn điện ảnh
        Public SwayArcDeg As Double = 70.0        ' Góc quét mỗi phía 70 độ
        Public CycleMode As String = "FULL_CYCLE" ' "FULL_CYCLE", "HALF_CYCLE", "2_CYCLES"

        ' 4. Thông số cự ly & chuyển động
        Public NearDistanceScale As Double = 0.30 ' Ép sát mặt tiền 0.30
        Public FarDistanceScale As Double = 0.60  ' Dãn xa mạn sườn 0.60
        Public SpeedMultiplier As Double = 2.00   ' Tốc độ bay 2.00x
        Public EasingMode As String = "EASE_IN_OUT"
        Public ApexHoldSeconds As Double = 0.35   ' Ghìm phanh tại điểm cận
        Public VerticalBobPercent As Double = 8.0 ' Nhấp nhô 8% chiều cao
        Public BankStart As Double = 60.0         ' Độ nghiêng BẮT ĐẦU: 60.0 độ
        Public BankEnd As Double = 0.0            ' Độ nghiêng KẾT THÚC: 0.0 độ
        Public HoldSeconds As Double = 0.0
    End Class

    Public Class Shot04Settings
        Public DurationSeconds As Double = 6.0     ' 6.0s (Chuẩn mặc định thực tế anh Tấn)
        Public FPS As Integer = 30
        Public RunMode As String = "PREVIEW"

        ' 1. Chế độ Đa Giác & Điểm soi (Polygon & Inspection Points)
        Public PointsMode As String = "CUSTOM_PICK" ' Tự chọn qua SelectSet
        Public CustomPickPoints As New List(Of Vec3)()
        Public CustomApproachVectors As New List(Of Vec3)() ' Lưu vector hướng nhìn camera khi click chọn chi tiết
        Public ApproachMode As String = "RECORDED_VIEW"   ' Theo Góc Nhìn Lúc Click Chọn / Màn Hình (Recorded View)

        ' 2. Bán kính đa giác & Cao độ góc nhìn (Saved Defaults)
        Public OrbitDistanceScale As Double = 2.00 ' Cự ly đa giác ngoài 2.00
        Public ElevationDeg As Double = 0.0        ' Cao độ góc nhìn 0.0 độ

        ' 3. Thông số Zoom Punch-In & FOV Macro (Saved Defaults)
        Public ZoomDollyScale As Double = 0.30     ' Cự ly ÉP SÁT khi Zoom 0.30
        Public NormalFOV As Double = 52.0          ' Góc mở thường 52.0 độ
        Public ZoomFOV As Double = 32.0            ' Góc mở Zoom Macro 32.0 độ

        ' 4. Gia tốc & Nhịp dừng ngắm (Micro-Hold & Dynamics)
        Public SpeedMultiplier As Double = 4.00    ' Tốc độ bay 4.00x (Chuẩn mặc định thực tế anh Tấn)
        Public MicroHoldSeconds As Double = 0.10   ' Thời gian ngắm tại mỗi điểm 0.10s (Chuẩn mặc định)
        Public BankApex As Double = 0.0            ' Độ nghiêng cánh khi lướt 0.0 độ
        Public EasingMode As String = "EASE_IN_OUT"
    End Class

    Public Class Shot05Settings
        Public DurationSeconds As Double = 4.5     ' Thời lượng tổng 4.5s
        Public FPS As Integer = 30
        Public RunMode As String = "PREVIEW"

        ' 1. Tiêu điểm Hero kết thúc & Góc 3/4 Xuất Phát (Khóa chuẩn mặc định thực tế anh Tấn)
        Public FocusHeroKey As String = "CENTER"        ' Mặc định: Tâm Toàn Bộ Skid
        Public StartCornerMode As String = "FRONT_LEFT" ' Góc 1: Trước - Trái (-X, -Z) [Mặc định]
        Public ViewAngleMode As String = "34_TOP"       ' 3/4 TRÊN
        Public ElevationDeg As Double = 25.0            ' Cao độ góc nhìn 25.0 độ
        Public OrbitRadiusScale As Double = 2.00        ' Bán kính xoay 2.00

        ' 2. Quỹ đạo bay xoay quanh mô hình (Helical Fly-Around Orbit)
        Public OrbitSweepDeg As Double = 720.0  ' Xoay 2 Vòng 720 độ
        Public OrbitDirection As String = "CCW" ' Ngược Chiều Kim Đồng Hồ (Trước -> Hông Phải)
        Public BankWhipDeg As Double = 0.0      ' Độ lật nghiêng cánh 0.0 độ
        Public ClosePassScale As Double = 1.10  ' Cự ly lướt sát mạn sườn 1.10

        ' 3. Thông số Hero Hold (Phanh cứng ngắm chi tiết)
        Public HeroHoldSec As Double = 0.20     ' Thời gian phanh cứng ngắm 0.20s
        Public HeroFOV As Double = 45.0         ' FOV khi ngắm Hero

        ' 4. Thông số Grand Escape (Bứt tốc thoát ly toàn cảnh)
        Public EscapeDistanceScale As Double = 1.0 ' Cự ly bung lùi xa thoát ly 1.0
        Public EscapeClimbScale As Double = 1.6    ' Cao độ bốc đầu 1.6
        Public EscapeFOV As Double = 60.0          ' FOV kết thúc 60.0 độ
        Public SpeedMultiplier As Double = 3.00    ' Tốc độ bay 3.00x
    End Class

    Public Class MasterMovieSettings
        Public IncludeShot01 As Boolean = True
        Public IncludeShot02 As Boolean = True
        Public IncludeShot03 As Boolean = True
        Public IncludeShot04 As Boolean = True
        Public IncludeShot05 As Boolean = True
    End Class

    ' ==============================================================================
    ' VIDEO EXPORT ENGINE CONTEXT (TIKTOK 9:16 & CINEMATIC MP4 PIPELINE)
    ' ==============================================================================
    Public Class VideoExportContext
        Public IsExporting As Boolean = False
        Public FrameFolder As String = ""
        Public FrameCounter As Integer = 1
        Public ExportWidth As Integer = 1920
        Public ExportHeight As Integer = 1080
        Public CurrentShotName As String = ""
        Public VideoFormat As String = "native_916" ' "tiktok_blur_916", "native_916", "widescreen_169"
        Public FPS As Integer = 30
        Public AudioMode As String = "auto"
    End Class

    ' --------------------------------------------------------------------------
    ' 4. QUỸ ĐẠO BÉZIER CHO CẢNH 1 & CẢNH 2
    ' --------------------------------------------------------------------------
    Public Class FlyInRail
        Public P0 As Vec3
        Public P1 As Vec3
        Public P2 As Vec3
        Public P3 As Vec3
        Public TargetStart As Vec3
        Public TargetEnd As Vec3

        Public Sub Build(ByVal model As ModelInfo, ByVal s As Shot01Settings)
            Dim C As Vec3 = model.Center
            Dim U As Vec3 = model.U : Dim V As Vec3 = model.V : Dim W As Vec3 = model.W
            Dim RU As Double = model.RU : Dim RV As Double = model.RV : Dim RH As Double = model.RH

            Dim diag As Double = If(model.Diag > 50.0, model.Diag, Math.Sqrt(4.0 * RU * RU + 4.0 * RV * RV + 4.0 * RH * RH))
            Dim halfFovRad As Double = (Math.Max(5.0, Math.Min(160.0, s.FOVEnd)) * 0.5) * Math.PI / 180.0
            Dim endScale As Double = Math.Max(0.05, Math.Min(10.0, s.EndDistanceScale))
            Dim fitDist As Double = (diag * 0.5) / Math.Tan(halfFovRad) * 1.18 * endScale

            Dim sgnU As Double = -1.0 : Dim sgnV As Double = 1.0
            Select Case s.CornerMode
                Case "FRONT_RIGHT" : sgnU = 1.0 : sgnV = -1.0
                Case "BACK_RIGHT"  : sgnU = 1.0 : sgnV = 1.0
                Case "FRONT_LEFT"  : sgnU = -1.0 : sgnV = -1.0
                Case Else          : sgnU = -1.0 : sgnV = 1.0
            End Select

            Dim elevAngleDeg As Double = -4.0
            Select Case s.ViewAngleMode
                Case "34_TOP"
                    elevAngleDeg = 28.0 : TargetStart = C : TargetEnd = C - 0.05 * RH * W
                Case "34_LEVEL"
                    elevAngleDeg = 0.0 : TargetStart = C : TargetEnd = C
                Case Else
                    elevAngleDeg = -4.0 : TargetStart = C + 0.15 * RH * W : TargetEnd = C + 0.20 * RH * W
            End Select

            Dim elevRad As Double = elevAngleDeg * Math.PI / 180.0
            Dim horizDist As Double = fitDist * Math.Cos(elevRad)
            Dim vertDist As Double = fitDist * Math.Sin(elevRad)

            Dim dirU As Double = sgnU * horizDist * 0.70710678
            Dim dirV As Double = sgnV * horizDist * 0.70710678
            Dim dirW As Double = vertDist

            Dim BaseOffset As New Vec3(dirU, dirW, dirV)
            Dim NormalSide As Vec3 = W.Cross(BaseOffset).Normalize()

            Dim distScale As Double = Math.Max(0.5, s.StartDistanceScale)
            Dim curve As Double = Math.Max(0.0, s.SwoopCurvature)

            P0 = C + BaseOffset * distScale
            P1 = C + BaseOffset * (distScale * 0.65) + (curve * 0.15 * RH) * W + (curve * 0.10 * RU) * NormalSide
            P2 = C + BaseOffset * (distScale * 0.35) + (curve * 0.06 * RH) * W + (curve * 0.04 * RU) * NormalSide
            P3 = C + BaseOffset
        End Sub

        Public Function EvaluateEye(ByVal t As Double) As Vec3
            t = Math.Max(0.0, Math.Min(1.0, t))
            Dim u As Double = 1.0 - t
            Dim tt As Double = t * t : Dim uu As Double = u * u
            Return uu * u * P0 + 3.0 * uu * t * P1 + 3.0 * u * tt * P2 + tt * t * P3
        End Function

        Public Function EvaluateTarget(ByVal t As Double) As Vec3
            t = Math.Max(0.0, Math.Min(1.0, t))
            Return Vec3.Lerp(TargetStart, TargetEnd, t)
        End Function
    End Class

    Public Class RailShot03
        Public CenterFocus As Vec3
        Public TargetFocus As Vec3
        Public EyeStart As Vec3
        Public TargetStart As Vec3
        Public BaseAngleRad As Double = -Math.PI * 0.5
        Public HasPrevEye As Boolean = False

        Public Sub Build(ByVal model As ModelInfo, ByVal heroes As Dictionary(Of String, HeroTarget), ByVal s03 As Shot03Settings, Optional ByVal fromPrevEye As Vec3 = Nothing, Optional ByVal fromPrevTarget As Vec3 = Nothing)
            If fromPrevEye IsNot Nothing Then HasPrevEye = True
            Dim C As Vec3 = model.Center
            Dim RU As Double = If(model.RU > 20.0, model.RU, 60.0)
            Dim RV As Double = If(model.RV > 20.0, model.RV, 100.0)
            Dim RH As Double = If(model.RH > 20.0, model.RH, 130.0)
            Dim diag As Double = If(model.Diag > 50.0, model.Diag, 360.0)

            ' 1. Xác định góc cơ sở và tâm máy (Chuẩn góc 3/4 đối xứng cân đều 2 bên 100%)
            Select Case s03.FocusMode
                Case "CORNER_1"
                    ' Góc 1: Trước - Trái (-X, -Z) chuẩn 45 độ cân đều 2 bên
                    CenterFocus = C
                    BaseAngleRad = -135.0 * Math.PI / 180.0
                Case "CORNER_2"
                    ' Góc 2: Trước - Phải (+X, -Z) chuẩn 45 độ cân đều 2 bên
                    CenterFocus = C
                    BaseAngleRad = -45.0 * Math.PI / 180.0
                Case "CORNER_3"
                    ' Góc 3: Sau - Phải (+X, +Z) chuẩn 45 độ cân đều 2 bên
                    CenterFocus = C
                    BaseAngleRad = 45.0 * Math.PI / 180.0
                Case "CORNER_4"
                    ' Góc 4: Sau - Trái (-X, +Z) chuẩn 45 độ cân đều 2 bên
                    CenterFocus = C
                    BaseAngleRad = 135.0 * Math.PI / 180.0
                Case "BACK_FACADE"
                    ' Mặt Sau máy (Quét giàn ống sau)
                    CenterFocus = C
                    BaseAngleRad = 90.0 * Math.PI / 180.0
                Case "SKID_CENTER"
                    ' Tâm toàn bộ skid
                    CenterFocus = C
                    BaseAngleRad = -135.0 * Math.PI / 180.0
                Case "CUSTOM_PICK"
                    ' Điểm chi tiết được chọn (SelectSet)
                    CenterFocus = If(s03.CustomPickPoint IsNot Nothing, s03.CustomPickPoint, C)
                    BaseAngleRad = -90.0 * Math.PI / 180.0
                Case Else
                    ' MẶT TIỀN PHÍA TRƯỚC (Góc 1 Trước-Trái ➔ Góc 2 Trước-Phải) [Khuyến nghị]
                    CenterFocus = C
                    BaseAngleRad = -90.0 * Math.PI / 180.0
            End Select

            ' 2. Xác định điểm ngắm Target và độ dốc (Mục 2 có hiệu lực rõ rệt 100%)
            Dim targetYShift As Double = 0.0
            Dim baseElevDeg As Double = 0.0
            Select Case s03.ViewAngleMode
                Case "34_BOTTOM"
                    baseElevDeg = -8.0
                    targetYShift = 0.20 * RH  ' Hất từ dưới bệ thép lên trên máy
                Case "34_TOP"
                    baseElevDeg = 28.0
                    targetYShift = -0.05 * RH ' Nhìn từ trên cao dốc xuống
                Case Else ' 34_LEVEL
                    baseElevDeg = 0.0
                    targetYShift = 0.0       ' Ngang tầm mắt chuẩn kỹ thuật
            End Select

            TargetFocus = CenterFocus + New Vec3(0, targetYShift, 0)

            ' 3. Điểm xuất phát
            If fromPrevEye IsNot Nothing Then
                EyeStart = fromPrevEye
                TargetStart = If(fromPrevTarget IsNot Nothing, fromPrevTarget, TargetFocus)
            Else
                Dim elevRadS As Double = baseElevDeg * Math.PI / 180.0
                Dim baseDist As Double = (diag * 0.5) / 0.466307658 * 1.18 * s03.FarDistanceScale
                Dim hDistS As Double = baseDist * Math.Cos(elevRadS)
                Dim vDistS As Double = baseDist * Math.Sin(elevRadS)
                Dim swayMaxRad As Double = (s03.SwayArcDeg * (s03.SwayPercent / 100.0)) * Math.PI / 180.0
                Dim startAngle As Double = BaseAngleRad - swayMaxRad
                EyeStart = CenterFocus + New Vec3(hDistS * Math.Cos(startAngle), vDistS, hDistS * Math.Sin(startAngle))
                TargetStart = TargetFocus
            End If
        End Sub

        Public Function EvaluateEye(ByVal t As Double, ByVal model As ModelInfo, ByVal s03 As Shot03Settings, ByRef outBankDeg As Double) As Vec3
            t = Math.Max(0.0, Math.Min(1.0, t))
            Dim CF As Vec3 = CenterFocus
            Dim diag As Double = If(model.Diag > 50.0, model.Diag, 360.0)
            Dim RH As Double = If(model.RH > 20.0, model.RH, 130.0)

            Dim nearDist As Double = (diag * 0.5) / 0.466307658 * 1.18 * s03.NearDistanceScale
            Dim farDist As Double = (diag * 0.5) / 0.466307658 * 1.18 * s03.FarDistanceScale
            Dim swayMaxRad As Double = (s03.SwayArcDeg * (s03.SwayPercent / 100.0)) * Math.PI / 180.0
            Dim bobMax As Double = (s03.VerticalBobPercent / 100.0) * RH

            Dim phase As Double
            If s03.CycleMode = "HALF_CYCLE" Then
                phase = -Math.PI * 0.5 + Math.PI * t
            ElseIf s03.CycleMode = "2_CYCLES" Then
                phase = -Math.PI * 0.5 + 4.0 * Math.PI * t
            Else
                phase = -Math.PI * 0.5 + 2.0 * Math.PI * t
            End If

            Dim swayOffset As Double = swayMaxRad * Math.Sin(phase)
            Dim normAngle As Double = Math.Abs(swayOffset) / Math.Max(0.001, swayMaxRad)

            Dim r As Double = nearDist + (farDist - nearDist) * normAngle
            Dim baseElevDeg As Double
            Select Case s03.ViewAngleMode
                Case "34_BOTTOM" : baseElevDeg = -8.0
                Case "34_TOP"    : baseElevDeg = 28.0
                Case Else        : baseElevDeg = 0.0
            End Select

            Dim curElevDeg As Double = baseElevDeg + (bobMax / Math.Max(1.0, r) * 57.3) * (1.0 - normAngle)
            Dim elevRad As Double = curElevDeg * Math.PI / 180.0

            Dim hR As Double = r * Math.Cos(elevRad)
            Dim vR As Double = r * Math.Sin(elevRad)

            Dim curAngle As Double = BaseAngleRad + swayOffset
            Dim idealX As Double = CF.X + hR * Math.Cos(curAngle)
            Dim idealY As Double = CF.Y + vR
            Dim idealZ As Double = CF.Z + hR * Math.Sin(curAngle)
            Dim idealEye As New Vec3(idealX, idealY, idealZ)

            Dim blend As Double = Math.Min(1.0, t / 0.15)
            Dim eye As Vec3 = Vec3.Lerp(EyeStart, idealEye, blend)
            Dim tSmooth As Double = t * t * (3.0 - 2.0 * t)
            Dim effBankStart As Double = If(HasPrevEye, 0.0, s03.BankStart)
            outBankDeg = effBankStart + (s03.BankEnd - effBankStart) * tSmooth

            Return eye
        End Function

        Public Function EvaluateTarget(ByVal t As Double) As Vec3
            t = Math.Max(0.0, Math.Min(1.0, t))
            Dim blend As Double = Math.Min(1.0, t / 0.15)
            Return Vec3.Lerp(TargetStart, TargetFocus, blend)
        End Function
    End Class

    Public Class RailShot02
        Public P0 As Vec3
        Public P1 As Vec3
        Public P2 As Vec3
        Public P3 As Vec3
        Public TargetStart As Vec3
        Public TargetEnd As Vec3

        Public Sub Build(ByVal model As ModelInfo, ByVal s02 As Shot02Settings, ByVal s01 As Shot01Settings, Optional ByVal fromPrevEye As Vec3 = Nothing, Optional ByVal fromPrevTarget As Vec3 = Nothing)
            Dim C As Vec3 = model.Center
            Dim U As Vec3 = model.U : Dim V As Vec3 = model.V : Dim W As Vec3 = model.W
            Dim RU As Double = model.RU : Dim RV As Double = model.RV : Dim RH As Double = model.RH
            Dim diag As Double = If(model.Diag > 50.0, model.Diag, Math.Sqrt(4.0 * RU * RU + 4.0 * RV * RV + 4.0 * RH * RH))

            ' 1. Xác định góc đầu
            Dim startCorner As String = s02.CornerStart
            If startCorner = "AUTO_C1" Then startCorner = s01.CornerMode

            Dim sgnU_S As Double = -1.0 : Dim sgnV_S As Double = 1.0
            Select Case startCorner
                Case "FRONT_RIGHT" : sgnU_S = 1.0 : sgnV_S = -1.0
                Case "BACK_RIGHT"  : sgnU_S = 1.0 : sgnV_S = 1.0
                Case "FRONT_LEFT"  : sgnU_S = -1.0 : sgnV_S = -1.0
                Case Else          : sgnU_S = -1.0 : sgnV_S = 1.0
            End Select

            ' 2. Xác định góc cuối
            Dim sgnU_E As Double = -1.0 : Dim sgnV_E As Double = -1.0
            Select Case s02.CornerEnd
                Case "FRONT_RIGHT" : sgnU_E = 1.0 : sgnV_E = -1.0
                Case "BACK_RIGHT"  : sgnU_E = 1.0 : sgnV_E = 1.0
                Case "BACK_LEFT"   : sgnU_E = -1.0 : sgnV_E = 1.0
                Case Else          : sgnU_E = -1.0 : sgnV_E = -1.0
            End Select

            ' 3. Tính P0 (Vị trí bắt đầu lùi)
            If fromPrevEye IsNot Nothing Then
                P0 = fromPrevEye
                TargetStart = If(fromPrevTarget IsNot Nothing, fromPrevTarget, C)
            Else
                Dim halfFovRadS As Double = (Math.Max(5.0, Math.Min(160.0, s02.FOVStart)) * 0.5) * Math.PI / 180.0
                Dim fitDistS As Double = (diag * 0.5) / Math.Tan(halfFovRadS) * 1.18 * s02.StartDistanceScale
                Dim elevDegS As Double = If(s01.ViewAngleMode = "34_TOP", 28.0, If(s01.ViewAngleMode = "34_LEVEL", 0.0, -4.0))
                Dim elevRadS As Double = elevDegS * Math.PI / 180.0
                Dim hDistS As Double = fitDistS * Math.Cos(elevRadS)
                Dim vDistS As Double = fitDistS * Math.Sin(elevRadS)
                P0 = C + New Vec3(sgnU_S * hDistS * 0.70710678, vDistS, sgnV_S * hDistS * 0.70710678)
                TargetStart = C + If(elevDegS < 0, 0.15 * RH * W, If(elevDegS > 0, -0.05 * RH * W, New Vec3(0, 0, 0)))
            End If

            ' 4. Tính P3 (Vị trí kết thúc ở xa)
            Dim halfFovRadE As Double = (Math.Max(5.0, Math.Min(160.0, s02.FOVEnd)) * 0.5) * Math.PI / 180.0
            Dim fitDistE As Double = (diag * 0.5) / Math.Tan(halfFovRadE) * 1.18 * s02.EndDistanceScale
            Dim elevDegE As Double = If(s02.ViewAngleModeEnd = "34_BOTTOM", -4.0, If(s02.ViewAngleModeEnd = "34_LEVEL", 0.0, 28.0))
            Dim elevRadE As Double = elevDegE * Math.PI / 180.0
            Dim hDistE As Double = fitDistE * Math.Cos(elevRadE)
            Dim vDistE As Double = fitDistE * Math.Sin(elevRadE)
            P3 = C + New Vec3(sgnU_E * hDistE * 0.70710678, vDistE, sgnV_E * hDistE * 0.70710678)
            TargetEnd = C + If(elevDegE < 0, 0.15 * RH * W, If(elevDegE > 0, -0.05 * RH * W, New Vec3(0, 0, 0)))

            ' 5. Quỹ đạo P1, P2 (Đường bay lùi: THẲNG hoặc CONG CÁNH CUNG)
            Dim flightVec As Vec3 = (P3 - P0)
            If s02.TrajectoryMode = "STRAIGHT" Then
                P1 = P0 + flightVec * 0.333
                P2 = P0 + flightVec * 0.666
            Else
                ' TÍNH VÉC-TƠ PHÁP TUYẾN NGANG 90 ĐỘ TRÊN MẶT PHẲNG SÀN X-Z (100% ORTHOGONAL)
                Dim horizFlight As New Vec3(flightVec.X, 0.0, flightVec.Z)
                Dim sideNormal As Vec3
                If horizFlight.Length() < 1E-3 Then
                    sideNormal = New Vec3(-sgnV_E, 0.0, sgnU_E).Normalize()
                Else
                    Dim uDir As Vec3 = horizFlight.Normalize()
                    Dim n1 As New Vec3(-uDir.Z, 0.0, uDir.X)
                    Dim n2 As New Vec3(uDir.Z, 0.0, -uDir.X)
                    ' Chọn hướng vồng ra ngoài xưởng (xa tâm mô hình C) để tuyệt đối không va chạm vào máy
                    Dim testDist1 As Double = ((P0 + n1 * 100.0) - C).Length()
                    Dim testDist2 As Double = ((P0 + n2 * 100.0) - C).Length()
                    sideNormal = If(testDist1 > testDist2, n1, n2)
                End If

                Dim curve As Double = Math.Max(0.0, s02.SwoopCurvature)
                ' Độ uốn vồng ngang sang sườn máy (từ 50cm đến trên 200cm rõ rệt)
                Dim lateralBulge As Double = curve * (0.015 * diag)
                ' Độ nâng nhẹ cao độ (tạo vòng cung 3D êm ái, giữ tầm nhìn bám sát máy)
                Dim verticalArch As Double = curve * (0.005 * RH)

                P1 = P0 + flightVec * 0.35 + sideNormal * lateralBulge + W * verticalArch
                P2 = P0 + flightVec * 0.70 + sideNormal * (lateralBulge * 1.15) + W * (verticalArch * 0.6)
            End If
        End Sub

        Public Function EvaluateEye(ByVal t As Double) As Vec3
            t = Math.Max(0.0, Math.Min(1.0, t))
            Dim u As Double = 1.0 - t
            Dim tt As Double = t * t : Dim uu As Double = u * u
            Return uu * u * P0 + 3.0 * uu * t * P1 + 3.0 * u * tt * P2 + tt * t * P3
        End Function

        Public Function EvaluateTarget(ByVal t As Double) As Vec3
            t = Math.Max(0.0, Math.Min(1.0, t))
            Return Vec3.Lerp(TargetStart, TargetEnd, t)
        End Function
    End Class

    Public Shared Function SmoothStepQuintic(ByVal t As Double) As Double
        t = Math.Max(0.0, Math.Min(1.0, t))
        Return t * t * t * (t * (t * 6.0 - 15.0) + 10.0)
    End Function

    ' --------------------------------------------------------------------------
    ' 5. QUÉT DỮ LIỆU SKID VÀ PHÁT HIỆN HERO TARGETS
    ' --------------------------------------------------------------------------
    Private Function ScanSkidModel(ByVal oDoc As Document) As ModelInfo
        Dim info As New ModelInfo()
        info.U = New Vec3(1, 0, 0)
        info.W = New Vec3(0, 1, 0)
        info.V = New Vec3(0, 0, 1)

        Try
            Dim oAsm As AssemblyDocument = CType(oDoc, AssemblyDocument)
            Dim box As Box = oAsm.ComponentDefinition.RangeBox
            info.MinPt = New Vec3(box.MinPoint.X, box.MinPoint.Y, box.MinPoint.Z)
            info.MaxPt = New Vec3(box.MaxPoint.X, box.MaxPoint.Y, box.MaxPoint.Z)
            info.Center = New Vec3((box.MinPoint.X + box.MaxPoint.X) * 0.5, (box.MinPoint.Y + box.MaxPoint.Y) * 0.5, (box.MinPoint.Z + box.MaxPoint.Z) * 0.5)

            info.RU = Math.Max(30.0, Math.Abs(box.MaxPoint.X - box.MinPoint.X) * 0.5)
            info.RH = Math.Max(40.0, Math.Abs(box.MaxPoint.Y - box.MinPoint.Y) * 0.5)
            info.RV = Math.Max(40.0, Math.Abs(box.MaxPoint.Z - box.MinPoint.Z) * 0.5)
            info.Diag = Math.Sqrt(info.RU * info.RU * 4.0 + info.RH * info.RH * 4.0 + info.RV * info.RV * 4.0)
        Catch
            info.Center = New Vec3(-8.19, 121.98, -5.78)
            info.MinPt = New Vec3(-69.89, -9.45, -111.55)
            info.MaxPt = New Vec3(53.50, 253.41, 100.00)
            info.RU = 61.70 : info.RH = 131.43 : info.RV = 105.78 : info.Diag = 360.0
        End Try

        Return info
    End Function

    Private Function DiscoverHeroes(ByVal oDoc As Document, ByVal model As ModelInfo) As Dictionary(Of String, HeroTarget)
        Dim dict As New Dictionary(Of String, HeroTarget)()

        Dim hPump As New HeroTarget() : hPump.Name = "Cụm Bơm" : hPump.Radius = 35.0 : hPump.Found = False
        Dim hUF As New HeroTarget() : hUF.Name = "Màng UF" : hUF.Radius = 45.0 : hUF.Found = False
        Dim hPanel As New HeroTarget() : hPanel.Name = "Tủ Điện" : hPanel.Radius = 40.0 : hPanel.Found = False

        hPump.Center = model.Center + (-0.35 * model.RU) * model.U + (-0.20 * model.RV) * model.V + (-0.25 * model.RH) * model.W
        hUF.Center = model.Center + (0.30 * model.RU) * model.U + (0.0 * model.RV) * model.V + (0.15 * model.RH) * model.W
        hPanel.Center = model.Center + (-0.25 * model.RU) * model.U + (0.35 * model.RV) * model.V + (0.05 * model.RH) * model.W

        Try
            If oDoc.DocumentType = DocumentTypeEnum.kAssemblyDocumentObject Then
                Dim oAsm As AssemblyDocument = CType(oDoc, AssemblyDocument)
                For Each occ As ComponentOccurrence In oAsm.ComponentDefinition.Occurrences
                    If occ.Visible Then
                        Dim n As String = occ.Name.ToLower()
                        If Not hPump.Found AndAlso (n.Contains("bom") OrElse n.Contains("pump")) Then
                            Dim b As Box = occ.RangeBox
                            hPump.Center = New Vec3((b.MinPoint.X + b.MaxPoint.X) * 0.5, (b.MinPoint.Y + b.MaxPoint.Y) * 0.5, (b.MinPoint.Z + b.MaxPoint.Z) * 0.5)
                            hPump.Found = True
                        ElseIf Not hUF.Found AndAlso (n.Contains("uf") OrElse n.Contains("membrane")) Then
                            Dim b As Box = occ.RangeBox
                            hUF.Center = New Vec3((b.MinPoint.X + b.MaxPoint.X) * 0.5, (b.MinPoint.Y + b.MaxPoint.Y) * 0.5, (b.MinPoint.Z + b.MaxPoint.Z) * 0.5)
                            hUF.Found = True
                        ElseIf Not hPanel.Found AndAlso (n.Contains("hop") OrElse n.Contains("panel") OrElse n.Contains("dien")) Then
                            Dim b As Box = occ.RangeBox
                            hPanel.Center = New Vec3((b.MinPoint.X + b.MaxPoint.X) * 0.5, (b.MinPoint.Y + b.MaxPoint.Y) * 0.5, (b.MinPoint.Z + b.MaxPoint.Z) * 0.5)
                            hPanel.Found = True
                        End If
                    End If
                Next
            End If
        Catch
        End Try

        dict("PUMP") = hPump
        dict("UF") = hUF
        dict("PANEL") = hPanel
        Return dict
    End Function

    ' --------------------------------------------------------------------------
    ' 6. THỰC THI CÁC CẢNH
    ' --------------------------------------------------------------------------
    Public Function ExecuteShot01(ByVal oDoc As Document, ByVal settings As Shot01Settings, _
                                  Optional ByRef outLastEye As Vec3 = Nothing, _
                                  Optional ByRef outLastTarget As Vec3 = Nothing, _
                                  Optional ByRef outLastUp As Vec3 = Nothing, _
                                  Optional ByRef outLastFOV As Double = 50.0, _
                                  Optional ByVal exportCtx As VideoExportContext = Nothing) As Boolean
        Dim oApp As Inventor.Application = oDoc.Parent
        Dim oView As Inventor.View = oApp.ActiveView
        Dim oCam As Inventor.Camera = oView.Camera
        Dim tg As TransientGeometry = oApp.TransientGeometry

        Dim model As ModelInfo = ScanSkidModel(oDoc)
        Dim rail As New FlyInRail()
        rail.Build(model, settings)

        Dim effectiveDur As Double = settings.DurationSeconds / Math.Max(0.05, settings.SpeedMultiplier)
        Dim totalFrames As Integer = Math.Max(10, CInt(effectiveDur * settings.FPS))

        oCam.Perspective = True

        Dim lastEye As Vec3 = rail.P3
        Dim lastTarget As Vec3 = rail.TargetEnd
        Dim lastUp As New Vec3(0, 1, 0)
        Dim lastFOV As Double = settings.FOVEnd

        ' Pha 1: Bay vào Fit View
        For frame As Integer = 0 To totalFrames
            If CheckEscapeKey() Then
                MessageBox.Show("Đã dừng Cảnh 1 (Phím ESC)", "WT3D WhipCam", MessageBoxButtons.OK, MessageBoxIcon.Information)
                Return False
            End If

            Dim tRaw As Double = CDbl(frame) / CDbl(totalFrames)
            Dim tSmooth As Double = SmoothStepQuintic(tRaw)

            Dim eye As Vec3 = rail.EvaluateEye(tSmooth)
            Dim targetPt As Vec3 = rail.EvaluateTarget(tSmooth)

            Dim curFOV As Double = settings.FOVStart + (settings.FOVEnd - settings.FOVStart) * tSmooth
            Dim curBankDeg As Double = settings.BankStart + (settings.BankEnd - settings.BankStart) * tSmooth
            Dim bankRad As Double = curBankDeg * Math.PI / 180.0

            Dim forward As Vec3 = (targetPt - eye).Normalize()
            Dim worldUp As New Vec3(0, 1, 0)
            Dim camRight As Vec3 = worldUp.Cross(forward).Normalize()
            If camRight.Length() < 1E-6 Then camRight = New Vec3(1, 0, 0)
            Dim camUp0 As Vec3 = forward.Cross(camRight).Normalize()
            Dim rolledUp As Vec3 = camUp0 * Math.Cos(bankRad) + camRight * Math.Sin(bankRad)

            lastEye = eye : lastTarget = targetPt : lastUp = rolledUp : lastFOV = curFOV

            oCam.Eye = tg.CreatePoint(eye.X, eye.Y, eye.Z)
            oCam.Target = tg.CreatePoint(targetPt.X, targetPt.Y, targetPt.Z)
            oCam.UpVector = tg.CreateUnitVector(rolledUp.X, rolledUp.Y, rolledUp.Z)
            oCam.PerspectiveAngle = curFOV * Math.PI / 180.0
            oCam.ApplyWithoutTransition()

            If exportCtx IsNot Nothing AndAlso exportCtx.IsExporting Then
                CaptureVideoFrame(oCam, exportCtx, oApp)
                SafeYield(2)
            Else
                If settings.RunMode = "PREVIEW" Then
                    System.Threading.Thread.Sleep(CInt(1000.0 / settings.FPS))
                    System.Windows.Forms.Application.DoEvents()
                End If
            End If
        Next

        ' Pha 2: Dừng ngắm tĩnh tại Fit View
        If settings.HoldSeconds > 0.0 Then
            Dim holdFrames As Integer = Math.Max(1, CInt(settings.HoldSeconds * settings.FPS))
            For frame As Integer = 0 To holdFrames
                If CheckEscapeKey() Then
                    MessageBox.Show("Đã dừng Cảnh 1 (Phím ESC)", "WT3D WhipCam", MessageBoxButtons.OK, MessageBoxIcon.Information)
                    Return False
                End If
                If exportCtx IsNot Nothing AndAlso exportCtx.IsExporting Then
                    CaptureVideoFrame(oCam, exportCtx, oApp)
                    SafeYield(2)
                Else
                    If settings.RunMode = "PREVIEW" Then
                        System.Threading.Thread.Sleep(CInt(1000.0 / settings.FPS))
                        System.Windows.Forms.Application.DoEvents()
                    End If
                End If
            Next
        End If

        ' Pha 3: Bay ra xa lại nếu bật trong Cảnh 1
        If settings.EnableFlyOut AndAlso settings.FlyOutDuration > 0.0 Then
            Dim effectiveDurOut As Double = settings.FlyOutDuration / Math.Max(0.05, settings.SpeedMultiplier)
            Dim totalFramesOut As Integer = Math.Max(10, CInt(effectiveDurOut * settings.FPS))

            For frame As Integer = 0 To totalFramesOut
                If CheckEscapeKey() Then
                    MessageBox.Show("Đã dừng Cảnh 1 (Phím ESC)", "WT3D WhipCam", MessageBoxButtons.OK, MessageBoxIcon.Information)
                    Return False
                End If

                Dim tRaw As Double = CDbl(frame) / CDbl(totalFramesOut)
                Dim tSmooth As Double = SmoothStepQuintic(tRaw)
                Dim tRail As Double = 1.0 - tSmooth

                Dim eye As Vec3 = rail.EvaluateEye(tRail)
                Dim targetPt As Vec3 = rail.EvaluateTarget(tRail)

                Dim curFOV As Double = settings.FOVStart + (settings.FOVEnd - settings.FOVStart) * tRail
                Dim curBankDeg As Double = settings.BankStart + (settings.BankEnd - settings.BankStart) * tRail
                Dim bankRad As Double = curBankDeg * Math.PI / 180.0

                Dim forward As Vec3 = (targetPt - eye).Normalize()
                Dim worldUp As New Vec3(0, 1, 0)
                Dim camRight As Vec3 = worldUp.Cross(forward).Normalize()
                If camRight.Length() < 1E-6 Then camRight = New Vec3(1, 0, 0)
                Dim camUp0 As Vec3 = forward.Cross(camRight).Normalize()
                Dim rolledUp As Vec3 = camUp0 * Math.Cos(bankRad) + camRight * Math.Sin(bankRad)

                lastEye = eye : lastTarget = targetPt : lastUp = rolledUp : lastFOV = curFOV

                oCam.Eye = tg.CreatePoint(eye.X, eye.Y, eye.Z)
                oCam.Target = tg.CreatePoint(targetPt.X, targetPt.Y, targetPt.Z)
                oCam.UpVector = tg.CreateUnitVector(rolledUp.X, rolledUp.Y, rolledUp.Z)
                oCam.PerspectiveAngle = curFOV * Math.PI / 180.0
                oCam.ApplyWithoutTransition()

                If exportCtx IsNot Nothing AndAlso exportCtx.IsExporting Then
                    CaptureVideoFrame(oCam, exportCtx, oApp)
                    SafeYield(2)
                Else
                    If settings.RunMode = "PREVIEW" Then
                        System.Threading.Thread.Sleep(CInt(1000.0 / settings.FPS))
                        System.Windows.Forms.Application.DoEvents()
                    End If
                End If
            Next
        End If

        outLastEye = lastEye : outLastTarget = lastTarget : outLastUp = lastUp : outLastFOV = lastFOV
        Return True
    End Function

    Public Function ExecuteShot02(ByVal oDoc As Document, ByVal s02 As Shot02Settings, ByVal s01 As Shot01Settings, ByVal model As ModelInfo, _
                                  Optional ByVal fromPrevEye As Vec3 = Nothing, _
                                  Optional ByVal fromPrevTarget As Vec3 = Nothing, _
                                  Optional ByRef outLastEye As Vec3 = Nothing, _
                                  Optional ByRef outLastTarget As Vec3 = Nothing, _
                                  Optional ByRef outLastUp As Vec3 = Nothing, _
                                  Optional ByRef outLastFOV As Double = 50.0, _
                                  Optional ByVal exportCtx As VideoExportContext = Nothing) As Boolean
        Dim oApp As Inventor.Application = oDoc.Parent
        Dim oView As Inventor.View = oApp.ActiveView
        Dim oCam As Inventor.Camera = oView.Camera
        Dim tg As TransientGeometry = oApp.TransientGeometry

        Dim rail As New RailShot02()
        rail.Build(model, s02, s01, fromPrevEye, fromPrevTarget)

        Dim effectiveDur As Double = s02.DurationSeconds / Math.Max(0.05, s02.SpeedMultiplier)
        Dim totalFrames As Integer = Math.Max(10, CInt(effectiveDur * s02.FPS))

        oCam.Perspective = True

        Dim lastEye As Vec3 = rail.P3
        Dim lastTarget As Vec3 = rail.TargetEnd
        Dim lastUp As New Vec3(0, 1, 0)
        Dim lastFOV As Double = s02.FOVEnd

        ' Pha 1: Bay lùi ra xa (Thẳng hoặc Cong)
        For frame As Integer = 0 To totalFrames
            If CheckEscapeKey() Then
                MessageBox.Show("Đã dừng Cảnh 2 (Phím ESC)", "WT3D WhipCam", MessageBoxButtons.OK, MessageBoxIcon.Information)
                Return False
            End If

            Dim tRaw As Double = CDbl(frame) / CDbl(totalFrames)
            Dim tSmooth As Double
            Select Case s02.EasingMode
                Case "EASE_OUT"
                    ' Chậm dần: Vút nhanh lúc đầu, hãm phanh êm dịu lúc kết thúc
                    tSmooth = 1.0 - Math.Pow(1.0 - tRaw, 3.0)
                Case "EASE_IN"
                    ' Nhanh dần: Bắt đầu từ tốn, tăng tốc phóng nhanh dần ra xa
                    tSmooth = Math.Pow(tRaw, 3.0)
                Case "LINEAR"
                    ' Đều đặn: Tốc độ đều tắp không đổi
                    tSmooth = tRaw
                Case Else
                    ' Mượt cả 2 đầu: Êm đầu chặng, nhanh giữa, êm cuối chặng
                    tSmooth = SmoothStepQuintic(tRaw)
            End Select

            Dim eye As Vec3 = rail.EvaluateEye(tSmooth)
            Dim targetPt As Vec3 = rail.EvaluateTarget(tSmooth)

            Dim effFOVStart As Double = If(fromPrevEye IsNot Nothing, s01.FOVEnd, s02.FOVStart)
            Dim curFOV As Double = effFOVStart + (s02.FOVEnd - effFOVStart) * tSmooth
            Dim effBankStart As Double = If(fromPrevEye IsNot Nothing, 0.0, s02.BankStart)
            Dim curBankDeg As Double = effBankStart + (s02.BankEnd - effBankStart) * tSmooth
            Dim bankRad As Double = curBankDeg * Math.PI / 180.0

            Dim forward As Vec3 = (targetPt - eye).Normalize()
            Dim worldUp As New Vec3(0, 1, 0)
            Dim camRight As Vec3 = worldUp.Cross(forward).Normalize()
            If camRight.Length() < 1E-6 Then camRight = New Vec3(1, 0, 0)
            Dim camUp0 As Vec3 = forward.Cross(camRight).Normalize()
            Dim rolledUp As Vec3 = camUp0 * Math.Cos(bankRad) + camRight * Math.Sin(bankRad)

            lastEye = eye : lastTarget = targetPt : lastUp = rolledUp : lastFOV = curFOV

            oCam.Eye = tg.CreatePoint(eye.X, eye.Y, eye.Z)
            oCam.Target = tg.CreatePoint(targetPt.X, targetPt.Y, targetPt.Z)
            oCam.UpVector = tg.CreateUnitVector(rolledUp.X, rolledUp.Y, rolledUp.Z)
            oCam.PerspectiveAngle = curFOV * Math.PI / 180.0
            oCam.ApplyWithoutTransition()

            If exportCtx IsNot Nothing AndAlso exportCtx.IsExporting Then
                CaptureVideoFrame(oCam, exportCtx, oApp)
                SafeYield(2)
            Else
                If s02.RunMode = "PREVIEW" Then
                    System.Threading.Thread.Sleep(CInt(1000.0 / s02.FPS))
                    System.Windows.Forms.Application.DoEvents()
                End If
            End If
        Next

        ' Pha 2: Dừng ngắm tại vị trí xa
        If s02.HoldSeconds > 0.0 Then
            Dim holdFrames As Integer = Math.Max(1, CInt(s02.HoldSeconds * s02.FPS))
            For frame As Integer = 0 To holdFrames
                If CheckEscapeKey() Then
                    MessageBox.Show("Đã dừng Cảnh 2 (Phím ESC)", "WT3D WhipCam", MessageBoxButtons.OK, MessageBoxIcon.Information)
                    Return False
                End If
                If exportCtx IsNot Nothing AndAlso exportCtx.IsExporting Then
                    CaptureVideoFrame(oCam, exportCtx, oApp)
                    SafeYield(2)
                Else
                    If s02.RunMode = "PREVIEW" Then
                        System.Threading.Thread.Sleep(CInt(1000.0 / s02.FPS))
                        System.Windows.Forms.Application.DoEvents()
                    End If
                End If
            Next
        End If

        outLastEye = lastEye : outLastTarget = lastTarget : outLastUp = lastUp : outLastFOV = lastFOV
        Return True
    End Function

    Public Function ExecuteShot03(ByVal oDoc As Document, ByVal s03 As Shot03Settings, ByVal s02 As Shot02Settings, ByVal s01 As Shot01Settings, ByVal model As ModelInfo, ByVal heroes As Dictionary(Of String, HeroTarget), _
                                  Optional ByVal fromPrevEye As Vec3 = Nothing, _
                                  Optional ByVal fromPrevTarget As Vec3 = Nothing, _
                                  Optional ByRef outLastEye As Vec3 = Nothing, _
                                  Optional ByRef outLastTarget As Vec3 = Nothing, _
                                  Optional ByRef outLastUp As Vec3 = Nothing, _
                                  Optional ByRef outLastFOV As Double = 50.0, _
                                  Optional ByVal exportCtx As VideoExportContext = Nothing) As Boolean
        Dim oApp As Inventor.Application = oDoc.Parent
        Dim oView As Inventor.View = oApp.ActiveView
        Dim oCam As Inventor.Camera = oView.Camera
        Dim tg As TransientGeometry = oApp.TransientGeometry

        Dim rail As New RailShot03()
        rail.Build(model, heroes, s03, fromPrevEye, fromPrevTarget)

        Dim effectiveDur As Double = s03.DurationSeconds / Math.Max(0.05, s03.SpeedMultiplier)
        Dim totalFrames As Integer = Math.Max(10, CInt(effectiveDur * s03.FPS))

        oCam.Perspective = True

        Dim lastEye As Vec3 = rail.EyeStart
        Dim lastTarget As Vec3 = rail.CenterFocus
        Dim lastUp As New Vec3(0, 1, 0)
        Dim lastFOV As Double = 50.0

        For frame As Integer = 0 To totalFrames
            If CheckEscapeKey() Then
                MessageBox.Show("Đã dừng Cảnh 3 (Phím ESC)", "WT3D WhipCam", MessageBoxButtons.OK, MessageBoxIcon.Information)
                Return False
            End If

            Dim tRaw As Double = CDbl(frame) / CDbl(totalFrames)
            Dim tSmooth As Double
            Select Case s03.EasingMode
                Case "EASE_OUT"
                    tSmooth = 1.0 - Math.Pow(1.0 - tRaw, 3.0)
                Case "EASE_IN"
                    tSmooth = Math.Pow(tRaw, 3.0)
                Case "LINEAR"
                    tSmooth = tRaw
                Case Else
                    tSmooth = SmoothStepQuintic(tRaw)
            End Select

            Dim curBankDeg As Double = 0.0
            Dim eye As Vec3 = rail.EvaluateEye(tSmooth, model, s03, curBankDeg)
            Dim targetPt As Vec3 = rail.EvaluateTarget(tSmooth)

            Dim bankRad As Double = curBankDeg * Math.PI / 180.0
            Dim forward As Vec3 = (targetPt - eye).Normalize()
            Dim worldUp As New Vec3(0, 1, 0)
            Dim camRight As Vec3 = worldUp.Cross(forward).Normalize()
            If camRight.Length() < 1E-6 Then camRight = New Vec3(1, 0, 0)
            Dim camUp0 As Vec3 = forward.Cross(camRight).Normalize()
            Dim rolledUp As Vec3 = camUp0 * Math.Cos(bankRad) + camRight * Math.Sin(bankRad)

            Dim effFOV As Double = If(fromPrevEye IsNot Nothing, s02.FOVEnd, 50.0)
            lastEye = eye : lastTarget = targetPt : lastUp = rolledUp : lastFOV = effFOV

            oCam.Eye = tg.CreatePoint(eye.X, eye.Y, eye.Z)
            oCam.Target = tg.CreatePoint(targetPt.X, targetPt.Y, targetPt.Z)
            oCam.UpVector = tg.CreateUnitVector(rolledUp.X, rolledUp.Y, rolledUp.Z)
            oCam.PerspectiveAngle = effFOV * Math.PI / 180.0
            oCam.ApplyWithoutTransition()

            If exportCtx IsNot Nothing AndAlso exportCtx.IsExporting Then
                CaptureVideoFrame(oCam, exportCtx, oApp)
                SafeYield(2)
            Else
                If s03.RunMode = "PREVIEW" Then
                    System.Threading.Thread.Sleep(CInt(1000.0 / s03.FPS))
                    System.Windows.Forms.Application.DoEvents()
                End If
            End If
        Next

        If s03.HoldSeconds > 0.0 Then
            Dim holdFrames As Integer = Math.Max(1, CInt(s03.HoldSeconds * s03.FPS))
            For frame As Integer = 0 To holdFrames
                If CheckEscapeKey() Then
                    MessageBox.Show("Đã dừng Cảnh 3 (Phím ESC)", "WT3D WhipCam", MessageBoxButtons.OK, MessageBoxIcon.Information)
                    Return False
                End If
                If exportCtx IsNot Nothing AndAlso exportCtx.IsExporting Then
                    CaptureVideoFrame(oCam, exportCtx, oApp)
                    SafeYield(2)
                Else
                    If s03.RunMode = "PREVIEW" Then
                        System.Threading.Thread.Sleep(CInt(1000.0 / s03.FPS))
                        System.Windows.Forms.Application.DoEvents()
                    End If
                End If
            Next
        End If

        outLastEye = lastEye : outLastTarget = lastTarget : outLastUp = lastUp : outLastFOV = lastFOV
        Return True
    End Function

    ' --------------------------------------------------------------------------
    ' 6.4. ENGINE THI CÔNG CẢNH 4: POLYGON SNAP-ORBIT & MULTI-POINT MACRO ZOOM
    ' --------------------------------------------------------------------------
    Public Function ExecuteShot04(ByVal oDoc As Document, ByVal s04 As Shot04Settings, ByVal s03 As Shot03Settings, ByVal s02 As Shot02Settings, ByVal s01 As Shot01Settings, ByVal model As ModelInfo, ByVal heroes As Dictionary(Of String, HeroTarget), _
                                  Optional ByVal fromPrevEye As Vec3 = Nothing, _
                                  Optional ByVal fromPrevTarget As Vec3 = Nothing, _
                                  Optional ByRef outLastEye As Vec3 = Nothing, _
                                  Optional ByRef outLastTarget As Vec3 = Nothing, _
                                  Optional ByRef outLastUp As Vec3 = Nothing, _
                                  Optional ByRef outLastFOV As Double = 50.0, _
                                  Optional ByVal exportCtx As VideoExportContext = Nothing) As Boolean
        Dim oApp As Inventor.Application = oDoc.Parent
        Dim oView As Inventor.View = oApp.ActiveView
        Dim oCam As Inventor.Camera = oView.Camera
        Dim tg As TransientGeometry = oApp.TransientGeometry

        Dim C As Vec3 = model.Center
        Dim RU As Double = model.RU
        Dim RV As Double = model.RV
        Dim RH As Double = model.RH
        Dim baseR As Double = Math.Sqrt(RU * RU + RV * RV)

        ' 1. Xác định danh sách các điểm mục tiêu (Targets)
        Dim targets As New List(Of Vec3)()
        Dim targetNames As New List(Of String)()

        If s04.PointsMode = "CUSTOM_PICK" AndAlso s04.CustomPickPoints.Count >= 2 Then
            For idx As Integer = 0 To s04.CustomPickPoints.Count - 1
                targets.Add(s04.CustomPickPoints(idx))
                targetNames.Add("Điểm chọn #" & (idx + 1).ToString())
            Next
        ElseIf s04.PointsMode = "3_POINTS" Then
            ' 3 Điểm chính: Bơm -> Màng RO/UF -> Tủ điện
            Dim tPump As Vec3 = If(heroes.ContainsKey("PUMP") AndAlso heroes("PUMP").Found, heroes("PUMP").Center, C + New Vec3(-0.35 * RU, -0.15 * RH, -0.35 * RV))
            Dim tMem As Vec3 = If(heroes.ContainsKey("MEMBRANE") AndAlso heroes("MEMBRANE").Found, heroes("MEMBRANE").Center, C + New Vec3(0.35 * RU, 0.20 * RH, 0.35 * RV))
            Dim tPanel As Vec3 = If(heroes.ContainsKey("PANEL") AndAlso heroes("PANEL").Found, heroes("PANEL").Center, C + New Vec3(-0.35 * RU, 0.10 * RH, 0.35 * RV))
            targets.Add(tPump) : targetNames.Add("Cụm Bơm Cao Áp")
            targets.Add(tMem) : targetNames.Add("Cụm Màng Lọc RO/UF")
            targets.Add(tPanel) : targetNames.Add("Tủ Điện Điều Khiển PLC")
        Else
            ' 4 Điểm TVC High-Tech: Bơm -> Đồng hồ áp -> Màng RO/UF -> Tủ điện
            Dim tPump As Vec3 = If(heroes.ContainsKey("PUMP") AndAlso heroes("PUMP").Found, heroes("PUMP").Center, C + New Vec3(-0.35 * RU, -0.15 * RH, -0.35 * RV))
            Dim tGauge As Vec3 = C + New Vec3(0.35 * RU, 0.0 * RH, -0.35 * RV)
            Dim tMem As Vec3 = If(heroes.ContainsKey("MEMBRANE") AndAlso heroes("MEMBRANE").Found, heroes("MEMBRANE").Center, C + New Vec3(0.35 * RU, 0.20 * RH, 0.35 * RV))
            Dim tPanel As Vec3 = If(heroes.ContainsKey("PANEL") AndAlso heroes("PANEL").Found, heroes("PANEL").Center, C + New Vec3(-0.35 * RU, 0.10 * RH, 0.35 * RV))
            targets.Add(tPump) : targetNames.Add("Cụm Bơm Cao Áp")
            targets.Add(tGauge) : targetNames.Add("Cụm Đồng Hồ & Van Tự Động")
            targets.Add(tMem) : targetNames.Add("Cụm Màng Lọc RO/UF")
            targets.Add(tPanel) : targetNames.Add("Tủ Điện Điều Khiển PLC")
        End If

        Dim numStages As Integer = targets.Count
        If numStages < 2 Then
            MessageBox.Show("Cần ít nhất 2 điểm mục tiêu cho Cảnh 4.", "WT3D WhipCam", MessageBoxButtons.OK, MessageBoxIcon.Warning)
            Return False
        End If

        ' 2. Tính toán Hướng Tiếp Cận & Các Đỉnh Đa Giác (Approach Vectors & Dynamic Polygon Nodes)
        Dim orbitR As Double = baseR * s04.OrbitDistanceScale
        Dim nearDist As Double = Math.Max(15.0, baseR * s04.ZoomDollyScale)

        Dim polyNodes As New List(Of Vec3)()
        Dim zoomInEyes As New List(Of Vec3)()
        Dim approachDirs As New List(Of Vec3)()

        For i As Integer = 0 To numStages - 1
            Dim curTgt As Vec3 = targets(i)
            Dim dirToHero As Vec3 = Nothing

            Select Case s04.ApproachMode
                Case "RECORDED_VIEW"
                    ' Ưu tiên lấy theo vector góc nhìn đã ghi nhận lúc người dùng click chọn điểm
                    If s04.PointsMode = "CUSTOM_PICK" AndAlso i < s04.CustomApproachVectors.Count AndAlso s04.CustomApproachVectors(i) IsNot Nothing Then
                        dirToHero = s04.CustomApproachVectors(i)
                    Else
                        Dim oCamNow As Inventor.Camera = oView.Camera
                        dirToHero = (New Vec3(oCamNow.Eye.X, oCamNow.Eye.Y, oCamNow.Eye.Z) - New Vec3(oCamNow.Target.X, oCamNow.Target.Y, oCamNow.Target.Z)).Normalize()
                    End If

                Case "ISOMETRIC_FL"
                    dirToHero = New Vec3(-0.7071, 0.5, -0.7071).Normalize()

                Case "ISOMETRIC_FR"
                    dirToHero = New Vec3(0.7071, 0.5, -0.7071).Normalize()

                Case "FRONT_LOOK"
                    dirToHero = New Vec3(0.0, 0.35, -1.0).Normalize()

                Case "TOP_DOWN"
                    dirToHero = New Vec3(0.0, 1.0, -0.2).Normalize()

                Case Else ' "AUTO_EXTERIOR" (Mặc định thông minh theo vị trí chi tiết trên mô hình)
                    Dim dx As Double = curTgt.X - C.X
                    Dim dz As Double = curTgt.Z - C.Z
                    Dim absDx As Double = Math.Abs(dx)
                    Dim absDz As Double = Math.Abs(dz)

                    Dim outX As Double = 0.0
                    Dim outZ As Double = 0.0

                    If absDz >= absDx * 0.6 Then
                        outZ = If(dz < 0, -1.0, 1.0)
                    End If
                    If absDx >= absDz * 0.6 Then
                        outX = If(dx < 0, -1.0, 1.0)
                    End If
                    If Math.Abs(outX) < 1E-4 AndAlso Math.Abs(outZ) < 1E-4 Then
                        outZ = -1.0
                    End If

                    Dim elRad As Double = Math.Max(0.0, s04.ElevationDeg) * Math.PI / 180.0
                    If elRad < 0.08 Then elRad = 0.20 ' ~12 độ nâng nhẹ để nhìn khối 3D rõ nét
                    Dim outY As Double = Math.Sin(elRad)
                    Dim horizScale As Double = Math.Cos(elRad)
                    dirToHero = New Vec3(outX * horizScale, outY, outZ * horizScale).Normalize()
            End Select

            If dirToHero Is Nothing OrElse dirToHero.Length() < 1E-5 Then
                dirToHero = New Vec3(-0.7071, 0.5, -0.7071).Normalize()
            End If

            approachDirs.Add(dirToHero)

            ' Vị trí phóng zoom cận cảnh (Macro Zoom-In Position)
            Dim zEye As Vec3 = curTgt + dirToHero * nearDist
            zoomInEyes.Add(zEye)

            ' Đỉnh ngoài đa giác tương ứng: nằm ngay trên trục tiếp cận ở cự ly orbitR
            Dim pNode As Vec3 = curTgt + dirToHero * orbitR
            polyNodes.Add(pNode)
        Next

        ' 3. Thiết lập thông số thời lượng & khung hình
        Dim effectiveDur As Double = s04.DurationSeconds / Math.Max(0.05, s04.SpeedMultiplier)
        Dim totalFrames As Integer = Math.Max(20, CInt(effectiveDur * s04.FPS))
        Dim framesPerStage As Integer = Math.Max(6, CInt(totalFrames / CDbl(numStages)))

        oCam.Perspective = True

        Dim lastEye As Vec3 = If(fromPrevEye IsNot Nothing, fromPrevEye, polyNodes(0))
        Dim lastTarget As Vec3 = If(fromPrevTarget IsNot Nothing, fromPrevTarget, targets(0))
        Dim lastUp As New Vec3(0, 1, 0)
        Dim lastFOV As Double = s04.NormalFOV

        Dim totalFramesRun As Integer = 0

        ' 4. Thực thi từng chặng đa giác (Stage-by-Stage Staccato Zoom)
        For stage As Integer = 0 To numStages - 1
            Dim curTarget As Vec3 = targets(stage)
            Dim curPolyNode As Vec3 = polyNodes(stage)
            Dim zoomInEye As Vec3 = zoomInEyes(stage)
            Dim dirToHero As Vec3 = approachDirs(stage)
            Dim prevPolyNode As Vec3 = If(stage = 0, (If(fromPrevEye IsNot Nothing, fromPrevEye, polyNodes(numStages - 1))), polyNodes(stage - 1))
            Dim stageStartTarget As Vec3 = If(stage = 0, (If(fromPrevTarget IsNot Nothing, fromPrevTarget, targets(0))), targets(stage - 1))

            ' --- PHA A: TIẾP CẬN & LAO VÀO PHÓNG ZOOM (Glide & Punch-In) ---
            Dim framesIn As Integer = Math.Max(4, CInt(framesPerStage * 0.60))
            For f As Integer = 0 To framesIn
                If CheckEscapeKey() Then
                    MessageBox.Show("Đã dừng Cảnh 4 (Phím ESC)", "WT3D WhipCam", MessageBoxButtons.OK, MessageBoxIcon.Information)
                    Return False
                End If

                Dim u As Double = CDbl(f) / CDbl(framesIn)
                Dim eye As Vec3
                Dim targetPt As Vec3
                Dim curFOV As Double = s04.NormalFOV
                Dim curBankDeg As Double = 0.0

                If u < 0.55 Then
                    ' 1. Lướt từ đỉnh đa giác trước sang đỉnh hiện tại (Nội suy mượt mà C2)
                    Dim w As Double = u / 0.55
                    Dim ws As Double = SmoothStepQuintic(w)
                    eye = Vec3.Lerp(prevPolyNode, curPolyNode, ws)
                    targetPt = Vec3.Lerp(stageStartTarget, curTarget, ws)
                    Dim baseFOV As Double = If(stage = 0 AndAlso fromPrevEye IsNot Nothing, 50.0, s04.NormalFOV)
                    curFOV = baseFOV + (s04.NormalFOV - baseFOV) * ws
                    curBankDeg = s04.BankApex * Math.Sin(Math.PI * ws)
                Else
                    ' 2. Punch-In lao thẳng vào chi tiết theo đúng hướng tiếp cận
                    Dim w As Double = (u - 0.55) / 0.45
                    Dim ws As Double = SmoothStepQuintic(w)
                    eye = Vec3.Lerp(curPolyNode, zoomInEye, ws)
                    targetPt = curTarget
                    curFOV = s04.NormalFOV + (s04.ZoomFOV - s04.NormalFOV) * ws
                    curBankDeg = s04.BankApex * (1.0 - ws)
                End If

                Dim bankRad As Double = curBankDeg * Math.PI / 180.0
                Dim forward As Vec3 = (targetPt - eye).Normalize()
                Dim worldUp As New Vec3(0, 1, 0)
                Dim camRight As Vec3 = worldUp.Cross(forward).Normalize()
                If camRight.Length() < 1E-6 Then camRight = New Vec3(1, 0, 0)
                Dim camUp0 As Vec3 = forward.Cross(camRight).Normalize()
                Dim rolledUp As Vec3 = camUp0 * Math.Cos(bankRad) + camRight * Math.Sin(bankRad)

                lastEye = eye : lastTarget = targetPt : lastUp = rolledUp : lastFOV = curFOV

                oCam.Eye = tg.CreatePoint(eye.X, eye.Y, eye.Z)
                oCam.Target = tg.CreatePoint(targetPt.X, targetPt.Y, targetPt.Z)
                oCam.UpVector = tg.CreateUnitVector(rolledUp.X, rolledUp.Y, rolledUp.Z)
                oCam.PerspectiveAngle = curFOV * Math.PI / 180.0
                oCam.ApplyWithoutTransition()

                totalFramesRun += 1
                If exportCtx IsNot Nothing AndAlso exportCtx.IsExporting Then
                    CaptureVideoFrame(oCam, exportCtx, oApp)
                    SafeYield(2)
                Else
                    If s04.RunMode = "PREVIEW" Then
                        System.Threading.Thread.Sleep(CInt(1000.0 / s04.FPS))
                        System.Windows.Forms.Application.DoEvents()
                    End If
                End If
            Next

            ' --- PHA B: DỪNG NGẮM TĨNH CÓ HIỆU LỰC CHÍNH XÁC (Hold Loop) ---
            If s04.MicroHoldSeconds > 0.0 Then
                Dim holdFrames As Integer = Math.Max(1, CInt(s04.MicroHoldSeconds * s04.FPS))
                For hf As Integer = 0 To holdFrames
                    If CheckEscapeKey() Then
                        MessageBox.Show("Đã dừng Cảnh 4 (Phím ESC)", "WT3D WhipCam", MessageBoxButtons.OK, MessageBoxIcon.Information)
                        Return False
                    End If

                    Dim hw As Double = CDbl(hf) / CDbl(holdFrames)
                    ' Vi trôi siêu nhẹ 0.6cm sống động
                    Dim microDrift As Vec3 = dirToHero * (Math.Sin(hw * Math.PI) * 0.6)
                    Dim hEye As Vec3 = zoomInEye + microDrift

                    Dim forward As Vec3 = (curTarget - hEye).Normalize()
                    Dim worldUp As New Vec3(0, 1, 0)
                    Dim camRight As Vec3 = worldUp.Cross(forward).Normalize()
                    If camRight.Length() < 1E-6 Then camRight = New Vec3(1, 0, 0)
                    Dim camUp0 As Vec3 = forward.Cross(camRight).Normalize()

                    lastEye = hEye : lastTarget = curTarget : lastUp = camUp0 : lastFOV = s04.ZoomFOV

                    oCam.Eye = tg.CreatePoint(hEye.X, hEye.Y, hEye.Z)
                    oCam.Target = tg.CreatePoint(curTarget.X, curTarget.Y, curTarget.Z)
                    oCam.UpVector = tg.CreateUnitVector(camUp0.X, camUp0.Y, camUp0.Z)
                    oCam.PerspectiveAngle = s04.ZoomFOV * Math.PI / 180.0
                    oCam.ApplyWithoutTransition()

                    totalFramesRun += 1
                    If exportCtx IsNot Nothing AndAlso exportCtx.IsExporting Then
                        CaptureVideoFrame(oCam, exportCtx, oApp)
                        SafeYield(2)
                    Else
                        If s04.RunMode = "PREVIEW" Then
                            System.Threading.Thread.Sleep(CInt(1000.0 / s04.FPS))
                            System.Windows.Forms.Application.DoEvents()
                        End If
                    End If
                Next
            End If

            ' --- PHA C: SNAP PULL-BACK GIẬT LÙI BUNG RA NGOÀI (Pull-Back) ---
            Dim framesOut As Integer = Math.Max(3, CInt(framesPerStage * 0.40))
            For f As Integer = 0 To framesOut
                If CheckEscapeKey() Then
                    MessageBox.Show("Đã dừng Cảnh 4 (Phím ESC)", "WT3D WhipCam", MessageBoxButtons.OK, MessageBoxIcon.Information)
                    Return False
                End If

                Dim u As Double = CDbl(f) / CDbl(framesOut)
                Dim ws As Double = SmoothStepQuintic(u)

                Dim eye As Vec3 = Vec3.Lerp(zoomInEye, curPolyNode, ws)
                Dim targetPt As Vec3 = curTarget
                Dim curFOV As Double = s04.ZoomFOV + (s04.NormalFOV - s04.ZoomFOV) * ws

                Dim forward As Vec3 = (targetPt - eye).Normalize()
                Dim worldUp As New Vec3(0, 1, 0)
                Dim camRight As Vec3 = worldUp.Cross(forward).Normalize()
                If camRight.Length() < 1E-6 Then camRight = New Vec3(1, 0, 0)
                Dim camUp0 As Vec3 = forward.Cross(camRight).Normalize()

                lastEye = eye : lastTarget = targetPt : lastUp = camUp0 : lastFOV = curFOV

                oCam.Eye = tg.CreatePoint(eye.X, eye.Y, eye.Z)
                oCam.Target = tg.CreatePoint(targetPt.X, targetPt.Y, targetPt.Z)
                oCam.UpVector = tg.CreateUnitVector(camUp0.X, camUp0.Y, camUp0.Z)
                oCam.PerspectiveAngle = curFOV * Math.PI / 180.0
                oCam.ApplyWithoutTransition()

                totalFramesRun += 1
                If exportCtx IsNot Nothing AndAlso exportCtx.IsExporting Then
                    CaptureVideoFrame(oCam, exportCtx, oApp)
                    SafeYield(2)
                Else
                    If s04.RunMode = "PREVIEW" Then
                        System.Threading.Thread.Sleep(CInt(1000.0 / s04.FPS))
                        System.Windows.Forms.Application.DoEvents()
                    End If
                End If
            Next
        Next

        outLastEye = lastEye
        outLastTarget = lastTarget
        outLastUp = lastUp
        outLastFOV = lastFOV

        Return True
    End Function

    ' --------------------------------------------------------------------------
    ' 6.5. ENGINE THI CÔNG CẢNH 5: HELICAL ORBIT FLY-AROUND -> HERO HOLD -> GRAND ESCAPE
    ' --------------------------------------------------------------------------
    Public Function ExecuteShot05(ByVal oDoc As Document, ByVal s05 As Shot05Settings, ByVal s04 As Shot04Settings, ByVal s03 As Shot03Settings, ByVal s02 As Shot02Settings, ByVal s01 As Shot01Settings, ByVal model As ModelInfo, ByVal heroes As Dictionary(Of String, HeroTarget), _
                                  Optional ByVal fromPrevEye As Vec3 = Nothing, _
                                  Optional ByVal fromPrevTarget As Vec3 = Nothing, _
                                  Optional ByRef outLastEye As Vec3 = Nothing, _
                                  Optional ByRef outLastTarget As Vec3 = Nothing, _
                                  Optional ByRef outLastUp As Vec3 = Nothing, _
                                  Optional ByRef outLastFOV As Double = 50.0, _
                                  Optional ByVal exportCtx As VideoExportContext = Nothing) As Boolean
        Dim oApp As Inventor.Application = oDoc.Parent
        Dim oView As Inventor.View = oApp.ActiveView
        Dim oCam As Inventor.Camera = oView.Camera
        Dim tg As TransientGeometry = oApp.TransientGeometry

        Dim C As Vec3 = model.Center
        Dim RU As Double = model.RU
        Dim RV As Double = model.RV
        Dim RH As Double = model.RH
        Dim baseR As Double = Math.Sqrt(RU * RU + RV * RV)

        ' 1. Xác định vị trí Hero tâm điểm kết thúc
        Dim heroTargetPt As Vec3
        If s05.FocusHeroKey = "LAST_PICK" AndAlso s04.CustomPickPoints.Count > 0 Then
            heroTargetPt = s04.CustomPickPoints(s04.CustomPickPoints.Count - 1)
        ElseIf s05.FocusHeroKey = "CENTER" Then
            heroTargetPt = C
        ElseIf s05.FocusHeroKey = "PUMP" AndAlso heroes.ContainsKey("PUMP") AndAlso heroes("PUMP").Found Then
            heroTargetPt = heroes("PUMP").Center
        ElseIf s05.FocusHeroKey = "MEMBRANE" AndAlso heroes.ContainsKey("MEMBRANE") AndAlso heroes("MEMBRANE").Found Then
            heroTargetPt = heroes("MEMBRANE").Center
        ElseIf s05.FocusHeroKey = "PANEL" AndAlso heroes.ContainsKey("PANEL") AndAlso heroes("PANEL").Found Then
            heroTargetPt = heroes("PANEL").Center
        Else
            heroTargetPt = C
        End If

        ' 2. Thiết lập Điểm Xuất Phát & Góc 3/4 (Corner 3/4 & Orbit Parameters)
        Dim orbitR As Double = baseR * Math.Max(0.5, s05.OrbitRadiusScale)
        Dim elevRad As Double = s05.ElevationDeg * Math.PI / 180.0
        Dim camYOffset As Double = orbitR * Math.Tan(elevRad)

        Dim ptStart As Vec3 = Nothing

        ' Trong Master Showreel (hoặc khi nối cảnh): Bắt buộc kế thừa 100% tọa độ từ cảnh trước để tuyệt đối không nhảy giật
        If fromPrevEye IsNot Nothing Then
            ptStart = fromPrevEye
        ElseIf s05.StartCornerMode = "CURRENT_VIEW" Then
            Dim curCamNow As Inventor.Camera = oView.Camera
            ptStart = New Vec3(curCamNow.Eye.X, curCamNow.Eye.Y, curCamNow.Eye.Z)
        Else
            ' Tính tọa độ 4 góc 3/4 chuẩn công nghiệp
            Dim cornerAngDeg As Double = -135.0 ' Mặc định Góc 1: Trước - Trái (-X, -Z)
            Select Case s05.StartCornerMode
                Case "FRONT_RIGHT" : cornerAngDeg = -45.0  ' Góc 2: Trước - Phải (+X, -Z)
                Case "BACK_RIGHT"  : cornerAngDeg = 45.0   ' Góc 3: Sau - Phải (+X, +Z)
                Case "BACK_LEFT"   : cornerAngDeg = 135.0  ' Góc 4: Sau - Trái (-X, +Z)
                Case Else          : cornerAngDeg = -135.0 ' Góc 1: Trước - Trái (-X, -Z)
            End Select
            Dim cornerRad As Double = cornerAngDeg * Math.PI / 180.0
            ptStart = New Vec3(C.X + orbitR * Math.Cos(cornerRad), C.Y + camYOffset, C.Z + orbitR * Math.Sin(cornerRad))
        End If

        Dim startR As Double = Math.Sqrt((ptStart.X - C.X) * (ptStart.X - C.X) + (ptStart.Z - C.Z) * (ptStart.Z - C.Z))
        If startR < 10.0 Then startR = orbitR

        Dim theta0 As Double = Math.Atan2(ptStart.Z - C.Z, ptStart.X - C.X)
        Dim dirSign As Double = If(s05.OrbitDirection = "CW", -1.0, 1.0)
        Dim sweepRad As Double = dirSign * (s05.OrbitSweepDeg * Math.PI / 180.0)

        ' Bán kính lướt quỹ đạo xoay quanh mô hình
        Dim passR As Double = orbitR

        ' Điểm dừng ngắm Hero (ptHoldEye) tại cuối vòng xoay
        Dim holdAngle As Double = theta0 + sweepRad
        Dim ptHoldEye As Vec3 = heroTargetPt + New Vec3(Math.Cos(holdAngle), 0.35, Math.Sin(holdAngle)).Normalize() * (baseR * Math.Max(0.5, s05.ClosePassScale))

        ' Điểm thoát ly Grand Escape (ptEscapeEye): lùi vút ra xa theo hướng mở rộng
        Dim escapeDir As Vec3 = (ptHoldEye - C).Normalize()
        If escapeDir.Length() < 1E-5 Then escapeDir = New Vec3(-0.7071, 0.5, -0.7071).Normalize()
        Dim ptEscapeEye As Vec3 = C + escapeDir * (baseR * s05.EscapeDistanceScale) + New Vec3(0, s05.EscapeClimbScale * RH, 0)

        ' 3. Thiết lập khung hình
        Dim effectiveDur As Double = s05.DurationSeconds / Math.Max(0.05, s05.SpeedMultiplier)
        Dim totalFrames As Integer = Math.Max(30, CInt(effectiveDur * s05.FPS))

        oCam.Perspective = True

        Dim lastEye As Vec3 = ptStart
        Dim startTarget As Vec3 = If(fromPrevTarget IsNot Nothing, fromPrevTarget, C)
        Dim lastTarget As Vec3 = startTarget
        Dim lastUp As New Vec3(0, 1, 0)
        Dim startFOV As Double = If(fromPrevEye IsNot Nothing, s04.NormalFOV, 52.0)
        Dim lastFOV As Double = startFOV

        ' --- GIAI ĐOẠN 1: HELICAL FLY-AROUND ORBIT (Bay lượn xoay vòng quanh mô hình) ---
        Dim orbitFrames As Integer = Math.Max(15, CInt(totalFrames * 0.65))
        For frame As Integer = 0 To orbitFrames
            If CheckEscapeKey() Then
                MessageBox.Show("Đã dừng Cảnh 5 (Phím ESC)", "WT3D WhipCam", MessageBoxButtons.OK, MessageBoxIcon.Information)
                Return False
            End If

            Dim u As Double = CDbl(frame) / CDbl(orbitFrames)
            Dim ws As Double = SmoothStepQuintic(u)

            Dim curTheta As Double = theta0 + sweepRad * ws
            Dim curR As Double = startR + (passR - startR) * ws
            Dim curX As Double = C.X + curR * Math.Cos(curTheta)
            Dim curZ As Double = C.Z + curR * Math.Sin(curTheta)
            Dim curY As Double = ptStart.Y + (heroTargetPt.Y + 0.30 * RH - ptStart.Y) * ws + Math.Sin(ws * Math.PI) * (0.25 * RH)

            Dim eye As New Vec3(curX, curY, curZ)
            Dim targetPt As Vec3 = Vec3.Lerp(startTarget, heroTargetPt, ws)
            Dim curFOV As Double = startFOV + (s05.HeroFOV - startFOV) * ws
            Dim curBankDeg As Double = dirSign * s05.BankWhipDeg * Math.Sin(ws * Math.PI * 2.0)

            Dim bankRad As Double = curBankDeg * Math.PI / 180.0
            Dim forward As Vec3 = (targetPt - eye).Normalize()
            Dim worldUp As New Vec3(0, 1, 0)
            Dim camRight As Vec3 = worldUp.Cross(forward).Normalize()
            If camRight.Length() < 1E-6 Then camRight = New Vec3(1, 0, 0)
            Dim camUp0 As Vec3 = forward.Cross(camRight).Normalize()
            Dim rolledUp As Vec3 = camUp0 * Math.Cos(bankRad) + camRight * Math.Sin(bankRad)

            lastEye = eye : lastTarget = targetPt : lastUp = rolledUp : lastFOV = curFOV

            oCam.Eye = tg.CreatePoint(eye.X, eye.Y, eye.Z)
            oCam.Target = tg.CreatePoint(targetPt.X, targetPt.Y, targetPt.Z)
            oCam.UpVector = tg.CreateUnitVector(rolledUp.X, rolledUp.Y, rolledUp.Z)
            oCam.PerspectiveAngle = curFOV * Math.PI / 180.0
            oCam.ApplyWithoutTransition()

            If exportCtx IsNot Nothing AndAlso exportCtx.IsExporting Then
                CaptureVideoFrame(oCam, exportCtx, oApp)
                SafeYield(2)
            Else
                If s05.RunMode = "PREVIEW" Then
                    System.Threading.Thread.Sleep(CInt(1000.0 / s05.FPS))
                    System.Windows.Forms.Application.DoEvents()
                End If
            End If
        Next

        ' --- GIAI ĐOẠN 2: DỪNG NGẮM HERO CÓ HIỆU LỰC CHÍNH XÁC (Dedicated Hold Loop) ---
        If s05.HeroHoldSec > 0.0 Then
            Dim holdFrames As Integer = Math.Max(1, CInt(s05.HeroHoldSec * s05.FPS))
            For hf As Integer = 0 To holdFrames
                If CheckEscapeKey() Then
                    MessageBox.Show("Đã dừng Cảnh 5 (Phím ESC)", "WT3D WhipCam", MessageBoxButtons.OK, MessageBoxIcon.Information)
                    Return False
                End If

                Dim hw As Double = CDbl(hf) / CDbl(holdFrames)
                Dim drift As New Vec3(Math.Sin(hw * Math.PI) * 0.5, 0, Math.Cos(hw * Math.PI) * 0.5)
                Dim hEye As Vec3 = ptHoldEye + drift

                Dim forward As Vec3 = (heroTargetPt - hEye).Normalize()
                Dim worldUp As New Vec3(0, 1, 0)
                Dim camRight As Vec3 = worldUp.Cross(forward).Normalize()
                If camRight.Length() < 1E-6 Then camRight = New Vec3(1, 0, 0)
                Dim camUp0 As Vec3 = forward.Cross(camRight).Normalize()

                lastEye = hEye : lastTarget = heroTargetPt : lastUp = camUp0 : lastFOV = s05.HeroFOV

                oCam.Eye = tg.CreatePoint(hEye.X, hEye.Y, hEye.Z)
                oCam.Target = tg.CreatePoint(heroTargetPt.X, heroTargetPt.Y, heroTargetPt.Z)
                oCam.UpVector = tg.CreateUnitVector(camUp0.X, camUp0.Y, camUp0.Z)
                oCam.PerspectiveAngle = s05.HeroFOV * Math.PI / 180.0
                oCam.ApplyWithoutTransition()

                If exportCtx IsNot Nothing AndAlso exportCtx.IsExporting Then
                    CaptureVideoFrame(oCam, exportCtx, oApp)
                    SafeYield(2)
                Else
                    If s05.RunMode = "PREVIEW" Then
                        System.Threading.Thread.Sleep(CInt(1000.0 / s05.FPS))
                        System.Windows.Forms.Application.DoEvents()
                    End If
                End If
            Next
        End If

        ' --- GIAI ĐOẠN 3: GRAND ESCAPE REVEAL (Bứt tốc thoát ly lùi ra xa & Bốc đầu) ---
        Dim escapeFrames As Integer = Math.Max(10, CInt(totalFrames * 0.35))
        For frame As Integer = 0 To escapeFrames
            If CheckEscapeKey() Then
                MessageBox.Show("Đã dừng Cảnh 5 (Phím ESC)", "WT3D WhipCam", MessageBoxButtons.OK, MessageBoxIcon.Information)
                Return False
            End If

            Dim u As Double = CDbl(frame) / CDbl(escapeFrames)
            Dim ws As Double = SmoothStepQuintic(u)

            Dim eye As Vec3 = Vec3.Lerp(ptHoldEye, ptEscapeEye, ws)
            Dim targetPt As Vec3 = Vec3.Lerp(heroTargetPt, C, ws)
            Dim curFOV As Double = s05.HeroFOV + (s05.EscapeFOV - s05.HeroFOV) * ws
            Dim curBankDeg As Double = 4.0 * Math.Sin(Math.PI * ws)

            Dim bankRad As Double = curBankDeg * Math.PI / 180.0
            Dim forward As Vec3 = (targetPt - eye).Normalize()
            Dim worldUp As New Vec3(0, 1, 0)
            Dim camRight As Vec3 = worldUp.Cross(forward).Normalize()
            If camRight.Length() < 1E-6 Then camRight = New Vec3(1, 0, 0)
            Dim camUp0 As Vec3 = forward.Cross(camRight).Normalize()
            Dim rolledUp As Vec3 = camUp0 * Math.Cos(bankRad) + camRight * Math.Sin(bankRad)

            lastEye = eye : lastTarget = targetPt : lastUp = rolledUp : lastFOV = curFOV

            oCam.Eye = tg.CreatePoint(eye.X, eye.Y, eye.Z)
            oCam.Target = tg.CreatePoint(targetPt.X, targetPt.Y, targetPt.Z)
            oCam.UpVector = tg.CreateUnitVector(rolledUp.X, rolledUp.Y, rolledUp.Z)
            oCam.PerspectiveAngle = curFOV * Math.PI / 180.0
            oCam.ApplyWithoutTransition()

            If exportCtx IsNot Nothing AndAlso exportCtx.IsExporting Then
                CaptureVideoFrame(oCam, exportCtx, oApp)
                SafeYield(2)
            Else
                If s05.RunMode = "PREVIEW" Then
                    System.Threading.Thread.Sleep(CInt(1000.0 / s05.FPS))
                    System.Windows.Forms.Application.DoEvents()
                End If
            End If
        Next

        outLastEye = lastEye
        outLastTarget = lastTarget
        outLastUp = lastUp
        outLastFOV = lastFOV

        Return True
    End Function


    ' --------------------------------------------------------------------------
    ' CƠ CHẾ LƯU TRỮ ĐIỂM VĨNH VIỄN (DUAL PERSISTENCE: ATTRIBUTESETS + JSON)
    ' --------------------------------------------------------------------------
    Public Shared Sub SavePointsToStorage(ByVal oDoc As Document, ByVal points As List(Of Vec3), ByVal dirs As List(Of Vec3), ByVal names As List(Of String))
        If points Is Nothing OrElse points.Count = 0 Then Return
        Try
            ' 1. Tạo chuỗi dữ liệu chuẩn hóa
            Dim sb As New System.Text.StringBuilder()
            For i As Integer = 0 To points.Count - 1
                Dim pName As String = If(i < names.Count AndAlso Not String.IsNullOrEmpty(names(i)), names(i), "Diem_" & (i + 1).ToString())
                pName = pName.Replace("|", "_").Replace(";", "_").Replace(vbCr, " ").Replace(vbLf, " ")
                Dim pt As Vec3 = points(i)
                Dim d As Vec3 = If(i < dirs.Count AndAlso dirs(i) IsNot Nothing, dirs(i), New Vec3(-0.7071, 0.5, -0.7071))
                sb.AppendFormat("{0}|{1:F4};{2:F4};{3:F4}|{4:F4};{5:F4};{6:F4}{7}", _
                    pName, pt.X, pt.Y, pt.Z, d.X, d.Y, d.Z, vbLf)
            Next
            Dim dataStr As String = sb.ToString()

            ' 2. Gắn trực tiếp vào Document AttributeSets của file CAD
            Try
                Dim attSets As AttributeSets = oDoc.AttributeSets
                Dim attSet As AttributeSet = Nothing
                If attSets.NameIsUsed("WT3D_WhipCam") Then
                    attSet = attSets.Item("WT3D_WhipCam")
                Else
                    attSet = attSets.Add("WT3D_WhipCam")
                End If

                If attSet.NameIsUsed("Shot04_Points") Then
                    attSet.Item("Shot04_Points").Value = dataStr
                Else
                    attSet.Add("Shot04_Points", ValueTypeEnum.kStringType, dataStr)
                End If
            Catch exDoc As Exception
            End Try

            ' 3. Xuất file Sidecar JSON bên cạnh file CAD & Backup toàn cục
            Dim filePaths As New List(Of String)()
            Try
                If Not String.IsNullOrEmpty(oDoc.FullFileName) Then
                    Dim sidecarPath As String = System.IO.Path.ChangeExtension(oDoc.FullFileName, ".whipcam_points.txt")
                    filePaths.Add(sidecarPath)
                End If
            Catch
            End Try
            filePaths.Add("D:\WT3D_Project\Z_Tools\WhipCam_Last_Saved_Points.txt")
            filePaths.Add("C:\Users\PHAN TRONG TAN\.gemini\antigravity\brain\0ae66afd-c144-4254-9d6b-7633e3f0365d\WhipCam_Last_Saved_Points.txt")

            For Each fp As String In filePaths
                Try
                    Dim dirName As String = System.IO.Path.GetDirectoryName(fp)
                    If Not String.IsNullOrEmpty(dirName) AndAlso Not System.IO.Directory.Exists(dirName) Then
                        System.IO.Directory.CreateDirectory(dirName)
                    End If
                    System.IO.File.WriteAllText(fp, dataStr, System.Text.Encoding.UTF8)
                Catch
                End Try
            Next
        Catch ex As Exception
        End Try
    End Sub

    Public Shared Function LoadPointsFromStorage(ByVal oDoc As Document, ByRef outPoints As List(Of Vec3), ByRef outDirs As List(Of Vec3), ByRef outNames As List(Of String)) As Boolean
        outPoints = New List(Of Vec3)()
        outDirs = New List(Of Vec3)()
        outNames = New List(Of String)()

        Dim rawData As String = ""

        ' 1. Ưu tiên đọc từ Document AttributeSets
        Try
            Dim attSets As AttributeSets = oDoc.AttributeSets
            If attSets.NameIsUsed("WT3D_WhipCam") Then
                Dim attSet As AttributeSet = attSets.Item("WT3D_WhipCam")
                If attSet.NameIsUsed("Shot04_Points") Then
                    rawData = CStr(attSet.Item("Shot04_Points").Value)
                End If
            End If
        Catch
        End Try

        ' 2. Nếu AttributeSets chưa có, thử đọc từ file Sidecar hoặc Backup
        If String.IsNullOrEmpty(rawData) Then
            Dim filePaths As New List(Of String)()
            Try
                If Not String.IsNullOrEmpty(oDoc.FullFileName) Then
                    filePaths.Add(System.IO.Path.ChangeExtension(oDoc.FullFileName, ".whipcam_points.txt"))
                End If
            Catch
            End Try
            filePaths.Add("D:\WT3D_Project\Z_Tools\WhipCam_Last_Saved_Points.txt")
            filePaths.Add("C:\Users\PHAN TRONG TAN\.gemini\antigravity\brain\0ae66afd-c144-4254-9d6b-7633e3f0365d\WhipCam_Last_Saved_Points.txt")

            For Each fp As String In filePaths
                Try
                    If System.IO.File.Exists(fp) Then
                        rawData = System.IO.File.ReadAllText(fp, System.Text.Encoding.UTF8)
                        If Not String.IsNullOrEmpty(rawData) Then Exit For
                    End If
                Catch
                End Try
            Next
        End If

        If String.IsNullOrEmpty(rawData) Then Return False

        ' 3. Parse chuỗi dữ liệu
        Try
            Dim lines As String() = rawData.Split(New Char() {ControlChars.Lf, ControlChars.Cr}, StringSplitOptions.RemoveEmptyEntries)
            For Each line As String In lines
                Dim parts As String() = line.Split("|"c)
                If parts.Length >= 2 Then
                    Dim pName As String = parts(0).Trim()
                    Dim ptParts As String() = parts(1).Split(";"c)
                    If ptParts.Length >= 3 Then
                        Dim px As Double = Double.Parse(ptParts(0), System.Globalization.CultureInfo.InvariantCulture)
                        Dim py As Double = Double.Parse(ptParts(1), System.Globalization.CultureInfo.InvariantCulture)
                        Dim pz As Double = Double.Parse(ptParts(2), System.Globalization.CultureInfo.InvariantCulture)
                        outPoints.Add(New Vec3(px, py, pz))
                        outNames.Add(pName)

                        If parts.Length >= 3 Then
                            Dim dirParts As String() = parts(2).Split(";"c)
                            If dirParts.Length >= 3 Then
                                Dim dx As Double = Double.Parse(dirParts(0), System.Globalization.CultureInfo.InvariantCulture)
                                Dim dy As Double = Double.Parse(dirParts(1), System.Globalization.CultureInfo.InvariantCulture)
                                Dim dz As Double = Double.Parse(dirParts(2), System.Globalization.CultureInfo.InvariantCulture)
                                outDirs.Add(New Vec3(dx, dy, dz).Normalize())
                            Else
                                outDirs.Add(New Vec3(-0.7071, 0.5, -0.7071).Normalize())
                            End If
                        Else
                            outDirs.Add(New Vec3(-0.7071, 0.5, -0.7071).Normalize())
                        End If
                    End If
                End If
            Next
            Return (outPoints.Count > 0)
        Catch ex As Exception
            Return False
        End Try
    End Function

    ' ==============================================================================
    ' CENTRAL VIDEO EXPORT PIPELINE (TIKTOK 9:16 & CINEMATIC MP4)
    ' ==============================================================================
    Public Sub RunExportPipeline(ByVal isMaster As Boolean, _
                                 ByVal oDoc As Document, _
                                 ByVal s01 As Shot01Settings, _
                                 ByVal s02 As Shot02Settings, _
                                 ByVal s03 As Shot03Settings, _
                                 ByVal s04 As Shot04Settings, _
                                 ByVal s05 As Shot05Settings, _
                                 ByVal model As ModelInfo, _
                                 ByVal heroes As Dictionary(Of String, HeroTarget), _
                                 ByVal currentTab As Integer, _
                                 ByVal runShot01 As Boolean, _
                                 ByVal runShot02 As Boolean, _
                                 ByVal runShot03 As Boolean, _
                                 ByVal runShot04 As Boolean, _
                                 ByVal runShot05 As Boolean, _
                                 ByVal videoFormat As String, _
                                 ByVal fpsVal As Integer, _
                                 ByVal audioMode As String, _
                                 ByVal openFolder As Boolean, _
                                 ByVal cleanupFrames As Boolean, _
                                 ByVal form As System.Windows.Forms.Form)
        Dim oApp As Inventor.Application = oDoc.Parent
        Dim baseDir As String = "d:\WT3D_Project\2_Video_Renders"
        If Not System.IO.Directory.Exists(baseDir) Then
            Try : System.IO.Directory.CreateDirectory(baseDir) : Catch : End Try
        End If

        Dim modelName As String = System.IO.Path.GetFileNameWithoutExtension(oDoc.FullFileName)
        If String.IsNullOrEmpty(modelName) Then modelName = "WT3D_Skid_Model"

        Dim shotTag As String = ""
        Dim shotTitleVN As String = ""
        If isMaster Then
            shotTag = "Master_Sequence"
            shotTitleVN = "SHOWREEL GHÉP LIÊN HOÀN 5 CẢNH"
        Else
            Select Case currentTab
                Case 0 : shotTag = "Shot01_GrandFlyIn" : shotTitleVN = "CẢNH 01: GRAND FLY-IN & FIT VIEW"
                Case 1 : shotTag = "Shot02_PullBackOrbit" : shotTitleVN = "CẢNH 02: PULL-BACK & ORBIT 3/4"
                Case 2 : shotTag = "Shot03_PendulumSway" : shotTitleVN = "CẢNH 03: CON LẮC MẶT TIỀN MÁY"
                Case 3 : shotTag = "Shot04_MacroZoom" : shotTitleVN = "CẢNH 04: MACRO ZOOM ĐA ĐIỂM"
                Case 4 : shotTag = "Shot05_HelicalEscape" : shotTitleVN = "CẢNH 05: HELICAL ORBIT & ESCAPE"
                Case Else : shotTag = "Shot_Custom" : shotTitleVN = "CINEMATIC SHOWREEL"
            End Select
        End If

        Dim runFolder As String = System.IO.Path.Combine(baseDir, modelName & "_" & shotTag & "_Frames")
        If System.IO.Directory.Exists(runFolder) Then
            For Each oldPng As String In System.IO.Directory.GetFiles(runFolder, "*.png")
                Try : System.IO.File.Delete(oldPng) : Catch : End Try
            Next
        Else
            System.IO.Directory.CreateDirectory(runFolder)
        End If

        Dim exportCtx As New VideoExportContext()
        exportCtx.IsExporting = True
        exportCtx.FrameFolder = runFolder
        exportCtx.FrameCounter = 1
        exportCtx.CurrentShotName = shotTitleVN
        exportCtx.VideoFormat = videoFormat
        exportCtx.FPS = fpsVal
        exportCtx.AudioMode = audioMode
        If videoFormat = "native_916" Then
            exportCtx.ExportWidth = 1080
            exportCtx.ExportHeight = 1920
        Else
            exportCtx.ExportWidth = 1920
            exportCtx.ExportHeight = 1080
        End If

        form.Visible = False
        oApp.StatusBarText = "🎬 Đang chụp từng khung hình Video 3D (Giữ ESC để dừng)..."

        Dim oldFlyOut As Boolean = s01.EnableFlyOut
        If isMaster Then s01.EnableFlyOut = False

        Dim aborted As Boolean = False
        Try
            Dim lastEye As Vec3 = Nothing
            Dim lastTarget As Vec3 = Nothing
            Dim lastUp As Vec3 = Nothing
            Dim lastFOV As Double = 50.0

            If Not isMaster Then
                Select Case currentTab
                    Case 0 : If Not ExecuteShot01(oDoc, s01, lastEye, lastTarget, lastUp, lastFOV, exportCtx) Then aborted = True
                    Case 1 : If Not ExecuteShot02(oDoc, s02, s01, model, Nothing, Nothing, lastEye, lastTarget, lastUp, lastFOV, exportCtx) Then aborted = True
                    Case 2 : If Not ExecuteShot03(oDoc, s03, s02, s01, model, heroes, Nothing, Nothing, lastEye, lastTarget, lastUp, lastFOV, exportCtx) Then aborted = True
                    Case 3 : If Not ExecuteShot04(oDoc, s04, s03, s02, s01, model, heroes, Nothing, Nothing, lastEye, lastTarget, lastUp, lastFOV, exportCtx) Then aborted = True
                    Case 4 : If Not ExecuteShot05(oDoc, s05, s04, s03, s02, s01, model, heroes, Nothing, Nothing, lastEye, lastTarget, lastUp, lastFOV, exportCtx) Then aborted = True
                End Select
            Else
                ' Ghép nối các cảnh được chọn
                If runShot01 Then
                    exportCtx.CurrentShotName = "CẢNH 01: GRAND FLY-IN"
                    If Not ExecuteShot01(oDoc, s01, lastEye, lastTarget, lastUp, lastFOV, exportCtx) Then aborted = True
                End If

                If Not aborted AndAlso runShot02 Then
                    exportCtx.CurrentShotName = "CẢNH 02: PULL-BACK & ORBIT 3/4"
                    Dim nEye As Vec3 = Nothing : Dim nTarget As Vec3 = Nothing : Dim nUp As Vec3 = Nothing : Dim nFOV As Double = 50.0
                    If Not ExecuteShot02(oDoc, s02, s01, model, lastEye, lastTarget, nEye, nTarget, nUp, nFOV, exportCtx) Then aborted = True
                    lastEye = nEye : lastTarget = nTarget : lastUp = nUp : lastFOV = nFOV
                End If

                If Not aborted AndAlso runShot03 Then
                    exportCtx.CurrentShotName = "CẢNH 03: CON LẮC MẶT TIỀN MÁY"
                    Dim nEye As Vec3 = Nothing : Dim nTarget As Vec3 = Nothing : Dim nUp As Vec3 = Nothing : Dim nFOV As Double = 50.0
                    If Not ExecuteShot03(oDoc, s03, s02, s01, model, heroes, lastEye, lastTarget, nEye, nTarget, nUp, nFOV, exportCtx) Then aborted = True
                    lastEye = nEye : lastTarget = nTarget : lastUp = nUp : lastFOV = nFOV
                End If

                If Not aborted AndAlso runShot04 Then
                    exportCtx.CurrentShotName = "CẢNH 04: MACRO ZOOM ĐA ĐIỂM"
                    Dim nEye As Vec3 = Nothing : Dim nTarget As Vec3 = Nothing : Dim nUp As Vec3 = Nothing : Dim nFOV As Double = 50.0
                    If Not ExecuteShot04(oDoc, s04, s03, s02, s01, model, heroes, lastEye, lastTarget, nEye, nTarget, nUp, nFOV, exportCtx) Then aborted = True
                    lastEye = nEye : lastTarget = nTarget : lastUp = nUp : lastFOV = nFOV
                End If

                If Not aborted AndAlso runShot05 Then
                    exportCtx.CurrentShotName = "CẢNH 05: HELICAL ORBIT & ESCAPE"
                    Dim nEye As Vec3 = Nothing : Dim nTarget As Vec3 = Nothing : Dim nUp As Vec3 = Nothing : Dim nFOV As Double = 50.0
                    If Not ExecuteShot05(oDoc, s05, s04, s03, s02, s01, model, heroes, lastEye, lastTarget, nEye, nTarget, nUp, nFOV, exportCtx) Then aborted = True
                End If
            End If
        Catch ex As Exception
            MessageBox.Show("Lỗi trong quá trình render frames: " & ex.Message, "WT3D Video Render", MessageBoxButtons.OK, MessageBoxIcon.Error)
            aborted = True
        Finally
            s01.EnableFlyOut = oldFlyOut
            form.Visible = True
        End Try

        If aborted OrElse exportCtx.FrameCounter <= 1 Then
            oApp.StatusBarText = "Đã dừng render video."
            Return
        End If

        ' Kích hoạt Python Exporter đóng gói MP4
        Dim outDir As String = System.IO.Path.Combine(baseDir, modelName)
        If Not System.IO.Directory.Exists(outDir) Then System.IO.Directory.CreateDirectory(outDir)
        Dim outMp4 As String = System.IO.Path.Combine(outDir, modelName & "_" & shotTag & "_" & videoFormat & ".mp4")

        Dim pyScript As String = "D:\WT3D_Project\Z_Tools\WhipCam_TikTok_Exporter.py"
        If Not System.IO.File.Exists(pyScript) Then
            MessageBox.Show("Không tìm thấy script: " & pyScript, "Thiếu Tool", MessageBoxButtons.OK, MessageBoxIcon.Warning)
            Return
        End If

        Dim q As String = Chr(34)
        Dim cmdArgs As String = q & pyScript & q & " --frames-dir " & q & runFolder & q & " --output-mp4 " & q & outMp4 & q & " --model-name " & q & modelName & q & " --shot-title " & q & shotTitleVN & q & " --format " & videoFormat & " --fps " & fpsVal.ToString()
        If audioMode <> "none" Then cmdArgs &= " --audio auto" Else cmdArgs &= " --audio none"
        If cleanupFrames Then cmdArgs &= " --cleanup"
        If openFolder Then cmdArgs &= " --open-folder"

        Try
            Dim psi As New System.Diagnostics.ProcessStartInfo("python.exe", cmdArgs)
            psi.WindowStyle = System.Diagnostics.ProcessWindowStyle.Hidden
            psi.CreateNoWindow = True
            Dim p As System.Diagnostics.Process = System.Diagnostics.Process.Start(psi)
            p.WaitForExit()

            If System.IO.File.Exists(outMp4) Then
                oApp.StatusBarText = "✔ Đã xuất video TikTok thành công: " & System.IO.Path.GetFileName(outMp4)
                MessageBox.Show("🎉 XUẤT VIDEO TIKTOK THÀNH CÔNG!" & vbCrLf & vbCrLf & _
                                "• Đường dẫn: " & outMp4 & vbCrLf & _
                                "• Định dạng: " & videoFormat & vbCrLf & _
                                "• Tổng số frames: " & (exportCtx.FrameCounter - 1).ToString() & " (" & fpsVal.ToString() & " FPS)", _
                                "WT3D Video Exporter", MessageBoxButtons.OK, MessageBoxIcon.Information)
            Else
                MessageBox.Show("Có lỗi khi tạo video MP4. Kiểm tra FFmpeg và Python.", "WT3D Video Exporter", MessageBoxButtons.OK, MessageBoxIcon.Warning)
            End If
        Catch ex As Exception
            MessageBox.Show("Lỗi gọi Python Exporter: " & ex.Message, "WT3D Video Exporter", MessageBoxButtons.OK, MessageBoxIcon.Error)
        End Try
    End Sub

    Public Sub Main()
        System.Threading.Thread.CurrentThread.CurrentCulture = System.Globalization.CultureInfo.InvariantCulture
        System.Threading.Thread.CurrentThread.CurrentUICulture = System.Globalization.CultureInfo.InvariantCulture

        Dim oApp As Inventor.Application = ThisApplication
        Dim oDoc As Document = oApp.ActiveDocument
        If oDoc Is Nothing Then
            MessageBox.Show("Hãy mở một mô hình Assembly trước.", "WT3D WhipCam", MessageBoxButtons.OK, MessageBoxIcon.Warning)
            Return
        End If

        Dim model As ModelInfo = ScanSkidModel(oDoc)
        Dim heroes As Dictionary(Of String, HeroTarget) = DiscoverHeroes(oDoc, model)

        Dim s01 As New Shot01Settings()
        Dim s02 As New Shot02Settings()
        Dim s03 As New Shot03Settings()
        Dim s04 As New Shot04Settings()
        Dim s05 As New Shot05Settings()
        Dim sMaster As New MasterMovieSettings()
        Dim customPointNames As New List(Of String)()

        ' TỰ ĐỘNG NẠP LẠI ĐIỂM ĐÃ LƯU TRƯỚC ĐÓ (AUTO-LOAD)
        If s04.CustomPickPoints.Count = 0 Then
            Dim autoPts As List(Of Vec3) = Nothing
            Dim autoDirs As List(Of Vec3) = Nothing
            Dim autoNames As List(Of String) = Nothing
            If LoadPointsFromStorage(oDoc, autoPts, autoDirs, autoNames) AndAlso autoPts.Count > 0 Then
                s04.CustomPickPoints = autoPts
                s04.CustomApproachVectors = autoDirs
                customPointNames = autoNames
                s04.PointsMode = "CUSTOM_PICK"
            End If
        End If
        Dim activeTabIndex As Integer = 3
        Dim formPendingAction As String = ""

        Dim keepStudioRunning As Boolean = True
        Do

        Dim form As New System.Windows.Forms.Form()
        form.Text = "WT3D WHIPCAM STUDIO — DIRECTOR MULTI-SHOT MASTER"
        form.Size = New System.Drawing.Size(615, 860)
        form.StartPosition = FormStartPosition.CenterScreen
        form.FormBorderStyle = FormBorderStyle.FixedDialog
        form.MaximizeBox = False
        form.MinimizeBox = False
        form.BackColor = System.Drawing.Color.FromArgb(248, 249, 250)
        form.Font = New System.Drawing.Font("Segoe UI", 9.0!, FontStyle.Regular)

        ' Header
        Dim lblTitle As New System.Windows.Forms.Label()
        lblTitle.Text = "WT3D WHIPCAM — MULTI-SHOT DIRECTOR STUDIO"
        lblTitle.UseMnemonic = False
        lblTitle.Font = New System.Drawing.Font("Segoe UI", 11.5!, FontStyle.Bold)
        lblTitle.ForeColor = System.Drawing.Color.FromArgb(20, 110, 60)
        lblTitle.Location = New System.Drawing.Point(18, 12)
        lblTitle.Size = New System.Drawing.Size(515, 24)
        form.Controls.Add(lblTitle)

        Dim lblSub As New System.Windows.Forms.Label()
        lblSub.Text = "Quản lý & tinh chỉnh độc lập từng Cảnh (Shot), và ghép phim Showreel liền mạch."
        lblSub.UseMnemonic = False
        lblSub.ForeColor = System.Drawing.Color.FromArgb(100, 110, 120)
        lblSub.Location = New System.Drawing.Point(20, 36)
        lblSub.Size = New System.Drawing.Size(515, 20)
        form.Controls.Add(lblSub)

        ' TabControl
        Dim tabStudio As New System.Windows.Forms.TabControl()
        tabStudio.Location = New System.Drawing.Point(16, 60)
        tabStudio.Size = New System.Drawing.Size(568, 660)
        tabStudio.Font = New System.Drawing.Font("Segoe UI", 9.0!, FontStyle.Bold)
        form.Controls.Add(tabStudio)

        ' ======================================================================
        ' TAB 1: CẢNH 1 — FLY-IN (FIT VIEW)
        ' ======================================================================
        Dim page01 As New System.Windows.Forms.TabPage()
        page01.Text = "🎬 CẢNH 1: FLY-IN"
        page01.BackColor = System.Drawing.Color.FromArgb(248, 249, 250)
        page01.AutoScroll = True
        tabStudio.TabPages.Add(page01)

        Dim grpCorner As New System.Windows.Forms.GroupBox()
        grpCorner.Text = " 1. HƯỚNG GÓC 3/4 (CHỌN 1 TRONG 4 GÓC QUANH GIÀN MÁY) "
        grpCorner.Location = New System.Drawing.Point(12, 10) : grpCorner.Size = New System.Drawing.Size(516, 62)
        grpCorner.BackColor = System.Drawing.Color.White
        page01.Controls.Add(grpCorner)

        Dim cboCorner As New System.Windows.Forms.ComboBox()
        cboCorner.DropDownStyle = ComboBoxStyle.DropDownList
        cboCorner.Location = New System.Drawing.Point(14, 24) : cboCorner.Size = New System.Drawing.Size(485, 26)
        cboCorner.Font = New System.Drawing.Font("Segoe UI", 9.0!, FontStyle.Bold)
        cboCorner.ForeColor = System.Drawing.Color.FromArgb(20, 100, 50)
        cboCorner.Items.Add("Góc 1: Trước - Trái (Mặt trước Bơm & Hông trái) [Khuyến nghị]")
        cboCorner.Items.Add("Góc 2: Trước - Phải (Mặt trước Bơm & Vỏ màng UF bên phải)")
        cboCorner.Items.Add("Góc 3: Sau - Phải (Đường ống xả/rửa sau & Màng UF)")
        cboCorner.Items.Add("Góc 4: Sau - Trái (Đường ống sau & Tủ điện điều khiển)")
        cboCorner.SelectedIndex = 3
        grpCorner.Controls.Add(cboCorner)

        Dim grpAngle As New System.Windows.Forms.GroupBox()
        grpAngle.Text = " 2. CAO ĐỘ GÓC NHÌN 3/4 (TRÊN / DƯỚI / NGANG) "
        grpAngle.Location = New System.Drawing.Point(12, 78) : grpAngle.Size = New System.Drawing.Size(516, 115)
        grpAngle.BackColor = System.Drawing.Color.White
        page01.Controls.Add(grpAngle)

        Dim radTop As New System.Windows.Forms.RadioButton()
        radTop.Text = "▲ 3/4 TRÊN   — Bao quát nóc bồn & toàn bộ sàn máy"
        radTop.UseMnemonic = False
        radTop.Location = New System.Drawing.Point(14, 22) : radTop.Size = New System.Drawing.Size(440, 22)
        radTop.Font = New System.Drawing.Font("Segoe UI", 9.0!, FontStyle.Bold)
        radTop.ForeColor = System.Drawing.Color.FromArgb(20, 100, 50)
        grpAngle.Controls.Add(radTop)

        Dim radBottom As New System.Windows.Forms.RadioButton()
        radBottom.Text = "▼ 3/4 DƯỚI   — Hất từ bệ thép lên hoành tráng, uy lực"
        radBottom.UseMnemonic = False
        radBottom.Location = New System.Drawing.Point(14, 52) : radBottom.Size = New System.Drawing.Size(440, 22)
        radBottom.Checked = True
        radBottom.Font = New System.Drawing.Font("Segoe UI", 9.0!, FontStyle.Bold)
        radBottom.ForeColor = System.Drawing.Color.FromArgb(140, 60, 10)
        grpAngle.Controls.Add(radBottom)

        Dim radLevel As New System.Windows.Forms.RadioButton()
        radLevel.Text = "■ 3/4 NGANG  — Ngang tầm mắt chuẩn kỹ thuật"
        radLevel.UseMnemonic = False
        radLevel.Location = New System.Drawing.Point(14, 82) : radLevel.Size = New System.Drawing.Size(440, 22)
        radLevel.ForeColor = System.Drawing.Color.FromArgb(60, 70, 80)
        grpAngle.Controls.Add(radLevel)

        Dim grpParams01 As New System.Windows.Forms.GroupBox()
        grpParams01.Text = " 3. THÔNG SỐ CHUYỂN ĐỘNG CẢNH 1 "
        grpParams01.Location = New System.Drawing.Point(12, 200) : grpParams01.Size = New System.Drawing.Size(516, 410)
        grpParams01.BackColor = System.Drawing.Color.White
        page01.Controls.Add(grpParams01)

        Dim lblDur As New System.Windows.Forms.Label()
        lblDur.Text = "Thời lượng cơ sở (giây):"
        lblDur.Location = New System.Drawing.Point(16, 20) : lblDur.Size = New System.Drawing.Size(220, 18)
        grpParams01.Controls.Add(lblDur)
        Dim numDur As New System.Windows.Forms.NumericUpDown()
        numDur.Location = New System.Drawing.Point(280, 18) : numDur.Size = New System.Drawing.Size(120, 22)
        numDur.DecimalPlaces = 1 : numDur.Increment = 0.5D : numDur.Minimum = 0.1D : numDur.Maximum = 300.0D
        numDur.Value = CDec(s01.DurationSeconds)
        grpParams01.Controls.Add(numDur)

        Dim lblSpeed As New System.Windows.Forms.Label()
        lblSpeed.Text = "Tốc độ bay (Hệ số Speed):"
        lblSpeed.Location = New System.Drawing.Point(16, 48) : lblSpeed.Size = New System.Drawing.Size(220, 18)
        grpParams01.Controls.Add(lblSpeed)
        Dim numSpeed As New System.Windows.Forms.NumericUpDown()
        numSpeed.Location = New System.Drawing.Point(280, 46) : numSpeed.Size = New System.Drawing.Size(120, 22)
        numSpeed.DecimalPlaces = 2 : numSpeed.Increment = 0.1D : numSpeed.Minimum = 0.01D : numSpeed.Maximum = 50.0D
        numSpeed.Value = CDec(s01.SpeedMultiplier)
        grpParams01.Controls.Add(numSpeed)

        Dim lblSpeedInfo As New System.Windows.Forms.Label()
        lblSpeedInfo.Location = New System.Drawing.Point(16, 72) : lblSpeedInfo.Size = New System.Drawing.Size(440, 18)
        lblSpeedInfo.Font = New System.Drawing.Font("Segoe UI", 8.25!, FontStyle.Italic)
        lblSpeedInfo.ForeColor = System.Drawing.Color.FromArgb(20, 120, 60)
        grpParams01.Controls.Add(lblSpeedInfo)

        Dim lblDist As New System.Windows.Forms.Label()
        lblDist.Text = "Cự ly XA xuất phát (x Model):"
        lblDist.Location = New System.Drawing.Point(16, 96) : lblDist.Size = New System.Drawing.Size(220, 18)
        grpParams01.Controls.Add(lblDist)
        Dim numDist As New System.Windows.Forms.NumericUpDown()
        numDist.Location = New System.Drawing.Point(280, 94) : numDist.Size = New System.Drawing.Size(120, 22)
        numDist.DecimalPlaces = 2 : numDist.Increment = 0.2D : numDist.Minimum = 0.1D : numDist.Maximum = 100.0D
        numDist.Value = CDec(s01.StartDistanceScale)
        grpParams01.Controls.Add(numDist)

        Dim lblDistE As New System.Windows.Forms.Label()
        lblDistE.Text = "Cự ly GẦN kết thúc (Fit View):"
        lblDistE.Location = New System.Drawing.Point(16, 124) : lblDistE.Size = New System.Drawing.Size(220, 18)
        grpParams01.Controls.Add(lblDistE)
        Dim numDistE As New System.Windows.Forms.NumericUpDown()
        numDistE.Location = New System.Drawing.Point(280, 122) : numDistE.Size = New System.Drawing.Size(120, 22)
        numDistE.DecimalPlaces = 2 : numDistE.Increment = 0.05D : numDistE.Minimum = 0.01D : numDistE.Maximum = 20.0D
        numDistE.Value = CDec(s01.EndDistanceScale)
        grpParams01.Controls.Add(numDistE)

        Dim lblCurve As New System.Windows.Forms.Label()
        lblCurve.Text = "Độ uốn lượn cánh cung:"
        lblCurve.Location = New System.Drawing.Point(16, 152) : lblCurve.Size = New System.Drawing.Size(220, 18)
        grpParams01.Controls.Add(lblCurve)
        Dim numCurve As New System.Windows.Forms.NumericUpDown()
        numCurve.Location = New System.Drawing.Point(280, 150) : numCurve.Size = New System.Drawing.Size(120, 22)
        numCurve.DecimalPlaces = 2 : numCurve.Increment = 0.1D : numCurve.Minimum = 0.0D : numCurve.Maximum = 50.0D
        numCurve.Value = CDec(s01.SwoopCurvature)
        grpParams01.Controls.Add(numCurve)

        Dim lblFovS As New System.Windows.Forms.Label()
        lblFovS.Text = "FOV lúc ở xa (độ):"
        lblFovS.Location = New System.Drawing.Point(16, 180) : lblFovS.Size = New System.Drawing.Size(220, 18)
        grpParams01.Controls.Add(lblFovS)
        Dim numFovS As New System.Windows.Forms.NumericUpDown()
        numFovS.Location = New System.Drawing.Point(280, 178) : numFovS.Size = New System.Drawing.Size(120, 22)
        numFovS.DecimalPlaces = 0 : numFovS.Increment = 1D : numFovS.Minimum = 2.0D : numFovS.Maximum = 160.0D
        numFovS.Value = CDec(s01.FOVStart)
        grpParams01.Controls.Add(numFovS)

        Dim lblFovE As New System.Windows.Forms.Label()
        lblFovE.Text = "FOV kết thúc Fit View (độ):"
        lblFovE.Location = New System.Drawing.Point(16, 208) : lblFovE.Size = New System.Drawing.Size(220, 18)
        grpParams01.Controls.Add(lblFovE)
        Dim numFovE As New System.Windows.Forms.NumericUpDown()
        numFovE.Location = New System.Drawing.Point(280, 206) : numFovE.Size = New System.Drawing.Size(120, 22)
        numFovE.DecimalPlaces = 0 : numFovE.Increment = 1D : numFovE.Minimum = 2.0D : numFovE.Maximum = 160.0D
        numFovE.Value = CDec(s01.FOVEnd)
        grpParams01.Controls.Add(numFovE)

        Dim lblBankS As New System.Windows.Forms.Label()
        lblBankS.Text = "Độ nghiêng BẮT ĐẦU (độ):"
        lblBankS.Location = New System.Drawing.Point(16, 236) : lblBankS.Size = New System.Drawing.Size(220, 18)
        grpParams01.Controls.Add(lblBankS)
        Dim numBankS As New System.Windows.Forms.NumericUpDown()
        numBankS.Location = New System.Drawing.Point(280, 234) : numBankS.Size = New System.Drawing.Size(120, 22)
        numBankS.DecimalPlaces = 1 : numBankS.Increment = 1.0D : numBankS.Minimum = -89.0D : numBankS.Maximum = 89.0D
        numBankS.Value = CDec(s01.BankStart)
        grpParams01.Controls.Add(numBankS)

        Dim lblBankE As New System.Windows.Forms.Label()
        lblBankE.Text = "Độ nghiêng KẾT THÚC (độ):"
        lblBankE.Location = New System.Drawing.Point(16, 264) : lblBankE.Size = New System.Drawing.Size(220, 18)
        grpParams01.Controls.Add(lblBankE)
        Dim numBankE As New System.Windows.Forms.NumericUpDown()
        numBankE.Location = New System.Drawing.Point(280, 262) : numBankE.Size = New System.Drawing.Size(120, 22)
        numBankE.DecimalPlaces = 1 : numBankE.Increment = 1.0D : numBankE.Minimum = -89.0D : numBankE.Maximum = 89.0D
        numBankE.Value = CDec(s01.BankEnd)
        grpParams01.Controls.Add(numBankE)

        Dim lblHold As New System.Windows.Forms.Label()
        lblHold.Text = "Thời gian dừng ngắm (giây):"
        lblHold.Location = New System.Drawing.Point(16, 292) : lblHold.Size = New System.Drawing.Size(220, 18)
        grpParams01.Controls.Add(lblHold)
        Dim numHold As New System.Windows.Forms.NumericUpDown()
        numHold.Location = New System.Drawing.Point(280, 290) : numHold.Size = New System.Drawing.Size(120, 22)
        numHold.DecimalPlaces = 1 : numHold.Increment = 0.5D : numHold.Minimum = 0.0D : numHold.Maximum = 120.0D
        numHold.Value = CDec(s01.HoldSeconds)
        grpParams01.Controls.Add(numHold)

        Dim chkFlyOut As New System.Windows.Forms.CheckBox()
        chkFlyOut.Text = "Sau khi dừng ngắm: Tự động bay vút ra xa lại"
        chkFlyOut.Location = New System.Drawing.Point(16, 320) : chkFlyOut.Size = New System.Drawing.Size(430, 22)
        chkFlyOut.Font = New System.Drawing.Font("Segoe UI", 9.0!, FontStyle.Bold)
        chkFlyOut.ForeColor = System.Drawing.Color.FromArgb(20, 100, 50)
        chkFlyOut.Checked = s01.EnableFlyOut
        grpParams01.Controls.Add(chkFlyOut)

        Dim lblDurOut As New System.Windows.Forms.Label()
        lblDurOut.Text = "Thời lượng bay ra xa (giây):"
        lblDurOut.Location = New System.Drawing.Point(16, 350) : lblDurOut.Size = New System.Drawing.Size(220, 18)
        grpParams01.Controls.Add(lblDurOut)
        Dim numDurOut As New System.Windows.Forms.NumericUpDown()
        numDurOut.Location = New System.Drawing.Point(280, 348) : numDurOut.Size = New System.Drawing.Size(120, 22)
        numDurOut.DecimalPlaces = 1 : numDurOut.Increment = 0.5D : numDurOut.Minimum = 0.1D : numDurOut.Maximum = 120.0D
        numDurOut.Value = CDec(s01.FlyOutDuration)
        grpParams01.Controls.Add(numDurOut)

        Dim updateSpeedLabel As Action = Sub()
            Dim durIn As Double = CDbl(numDur.Value)
            Dim spd As Double = CDbl(numSpeed.Value)
            Dim hold As Double = CDbl(numHold.Value)
            Dim flyOut As Boolean = chkFlyOut.Checked
            numDurOut.Enabled = flyOut
            lblDurOut.Enabled = flyOut

            Dim actualIn As Double = durIn / Math.Max(0.05, spd)
            Dim actualOut As Double = If(flyOut, CDbl(numDurOut.Value) / Math.Max(0.05, spd), 0.0)
            Dim totalT As Double = actualIn + hold + actualOut

            If flyOut Then
                lblSpeedInfo.Text = String.Format("▶ Vào: {0:F1}s | Ngắm: {1:F1}s | Ra: {2:F1}s  ➔  Tổng: {3:F1}s ({4:F2}x)", actualIn, hold, actualOut, totalT, spd)
            Else
                lblSpeedInfo.Text = String.Format("▶ Vào: {0:F1}s | Ngắm: {1:F1}s (Dừng Fit View)  ➔  Tổng: {2:F1}s ({3:F2}x)", actualIn, hold, totalT, spd)
            End If
        End Sub

        AddHandler numDur.ValueChanged, Sub(s As Object, e As EventArgs) updateSpeedLabel()
        AddHandler numSpeed.ValueChanged, Sub(s As Object, e As EventArgs) updateSpeedLabel()
        AddHandler numHold.ValueChanged, Sub(s As Object, e As EventArgs) updateSpeedLabel()
        AddHandler chkFlyOut.CheckedChanged, Sub(s As Object, e As EventArgs) updateSpeedLabel()
        AddHandler numDurOut.ValueChanged, Sub(s As Object, e As EventArgs) updateSpeedLabel()
        updateSpeedLabel()

        ' ======================================================================
        ' TAB 2: CẢNH 2 — BAY RA XA LẠI & ĐỔI GÓC 3/4 (PULL-BACK & ORBIT RE-FRAME)
        ' ======================================================================
        Dim page02 As New System.Windows.Forms.TabPage()
        page02.Text = "🎬 CẢNH 2: BAY RA XA (ĐỔI GÓC)"
        page02.BackColor = System.Drawing.Color.FromArgb(248, 249, 250)
        page02.AutoScroll = True
        tabStudio.TabPages.Add(page02)

        Dim grpCorners02 As New System.Windows.Forms.GroupBox()
        grpCorners02.Text = " 1. HƯỚNG GÓC 3/4 (BẮT ĐẦU & KẾT THÚC) "
        grpCorners02.Location = New System.Drawing.Point(12, 10) : grpCorners02.Size = New System.Drawing.Size(516, 100)
        grpCorners02.BackColor = System.Drawing.Color.White
        page02.Controls.Add(grpCorners02)

        Dim lblCornerS02 As New System.Windows.Forms.Label()
        lblCornerS02.Text = "Góc 3/4 BẮT ĐẦU (Đầu Cảnh 2):"
        lblCornerS02.Location = New System.Drawing.Point(14, 25) : lblCornerS02.Size = New System.Drawing.Size(180, 20)
        grpCorners02.Controls.Add(lblCornerS02)

        Dim cboCornerS02 As New System.Windows.Forms.ComboBox()
        cboCornerS02.DropDownStyle = ComboBoxStyle.DropDownList
        cboCornerS02.Location = New System.Drawing.Point(200, 22) : cboCornerS02.Size = New System.Drawing.Size(300, 25)
        cboCornerS02.Font = New System.Drawing.Font("Segoe UI", 9.0!, FontStyle.Bold)
        cboCornerS02.ForeColor = System.Drawing.Color.FromArgb(20, 100, 50)
        cboCornerS02.Items.Add("[Tự động] Kế thừa điểm dừng Cảnh 1 [Khuyến nghị]")
        cboCornerS02.Items.Add("Góc 1: Trước - Trái (-X, -Z)")
        cboCornerS02.Items.Add("Góc 2: Trước - Phải (+X, -Z)")
        cboCornerS02.Items.Add("Góc 3: Sau - Phải (+X, +Z)")
        cboCornerS02.Items.Add("Góc 4: Sau - Trái (-X, +Z)")
        cboCornerS02.SelectedIndex = 0
        grpCorners02.Controls.Add(cboCornerS02)

        Dim lblCornerE02 As New System.Windows.Forms.Label()
        lblCornerE02.Text = "Góc 3/4 KẾT THÚC (Cuối Cảnh 2):"
        lblCornerE02.Location = New System.Drawing.Point(14, 60) : lblCornerE02.Size = New System.Drawing.Size(180, 20)
        grpCorners02.Controls.Add(lblCornerE02)

        Dim cboCornerE02 As New System.Windows.Forms.ComboBox()
        cboCornerE02.DropDownStyle = ComboBoxStyle.DropDownList
        cboCornerE02.Location = New System.Drawing.Point(200, 57) : cboCornerE02.Size = New System.Drawing.Size(300, 25)
        cboCornerE02.Font = New System.Drawing.Font("Segoe UI", 9.0!, FontStyle.Bold)
        cboCornerE02.ForeColor = System.Drawing.Color.FromArgb(30, 60, 120)
        cboCornerE02.Items.Add("Góc 1: Trước - Trái (Đổi sang ngắm mặt trước Bơm) [Khuyến nghị]")
        cboCornerE02.Items.Add("Góc 2: Trước - Phải (Mặt trước & Vỏ màng UF)")
        cboCornerE02.Items.Add("Góc 3: Sau - Phải (Đường ống sau & Màng UF)")
        cboCornerE02.Items.Add("Góc 4: Sau - Trái (Giữ nguyên góc 4 lùi thẳng ra xa)")
        cboCornerE02.SelectedIndex = 0
        grpCorners02.Controls.Add(cboCornerE02)

        ' Bento 2 Cảnh 2: Cao độ góc nhìn 3/4 kết thúc (Trên / Dưới / Ngang)
        Dim grpAngle02 As New System.Windows.Forms.GroupBox()
        grpAngle02.Text = " 2. CAO ĐỘ GÓC 3/4 KẾT THÚC (TRÊN / DƯỚI / NGANG) "
        grpAngle02.Location = New System.Drawing.Point(12, 118) : grpAngle02.Size = New System.Drawing.Size(516, 115)
        grpAngle02.BackColor = System.Drawing.Color.White
        page02.Controls.Add(grpAngle02)

        Dim radTop02 As New System.Windows.Forms.RadioButton()
        radTop02.Text = "▲ 3/4 TRÊN   — Bao quát nóc bồn & toàn bộ sàn máy từ trên cao [Khuyến nghị]"
        radTop02.UseMnemonic = False
        radTop02.Location = New System.Drawing.Point(14, 22) : radTop02.Size = New System.Drawing.Size(445, 22)
        radTop02.Checked = (s02.ViewAngleModeEnd = "34_TOP")
        radTop02.Font = New System.Drawing.Font("Segoe UI", 9.0!, FontStyle.Bold)
        radTop02.ForeColor = System.Drawing.Color.FromArgb(20, 100, 50)
        grpAngle02.Controls.Add(radTop02)

        Dim radBottom02 As New System.Windows.Forms.RadioButton()
        radBottom02.Text = "▼ 3/4 DƯỚI   — Hất từ bệ thép lên hoành tráng, uy lực"
        radBottom02.UseMnemonic = False
        radBottom02.Location = New System.Drawing.Point(14, 52) : radBottom02.Size = New System.Drawing.Size(445, 22)
        radBottom02.Checked = (s02.ViewAngleModeEnd = "34_BOTTOM")
        radBottom02.Font = New System.Drawing.Font("Segoe UI", 9.0!, FontStyle.Bold)
        radBottom02.ForeColor = System.Drawing.Color.FromArgb(140, 60, 10)
        grpAngle02.Controls.Add(radBottom02)

        Dim radLevel02 As New System.Windows.Forms.RadioButton()
        radLevel02.Text = "■ 3/4 NGANG  — Ngang tầm mắt chuẩn kỹ thuật"
        radLevel02.UseMnemonic = False
        radLevel02.Location = New System.Drawing.Point(14, 82) : radLevel02.Size = New System.Drawing.Size(445, 22)
        radLevel02.Checked = (s02.ViewAngleModeEnd = "34_LEVEL")
        radLevel02.ForeColor = System.Drawing.Color.FromArgb(60, 70, 80)
        grpAngle02.Controls.Add(radLevel02)

        ' Bento 3 Cảnh 2: Quỹ đạo bay lùi
        Dim grpTraj02 As New System.Windows.Forms.GroupBox()
        grpTraj02.Text = " 3. QUỸ ĐẠO BAY LÙI (THẲNG HOẶC CONG) "
        grpTraj02.Location = New System.Drawing.Point(12, 240) : grpTraj02.Size = New System.Drawing.Size(516, 115)
        grpTraj02.BackColor = System.Drawing.Color.White
        page02.Controls.Add(grpTraj02)

        Dim radCurved02 As New System.Windows.Forms.RadioButton()
        radCurved02.Text = "BAY CONG  — Lượn cánh cung chữ C vồng ra ngoài xưởng mượt mà [Khuyến nghị]"
        radCurved02.UseMnemonic = False
        radCurved02.Location = New System.Drawing.Point(14, 22) : radCurved02.Size = New System.Drawing.Size(445, 22)
        radCurved02.Checked = (s02.TrajectoryMode = "CURVED")
        radCurved02.Font = New System.Drawing.Font("Segoe UI", 9.0!, FontStyle.Bold)
        radCurved02.ForeColor = System.Drawing.Color.FromArgb(20, 100, 50)
        grpTraj02.Controls.Add(radCurved02)

        Dim radStraight02 As New System.Windows.Forms.RadioButton()
        radStraight02.Text = "BAY THẲNG — Lùi thẳng tắp ra xa theo đường ngắm kỹ thuật"
        radStraight02.UseMnemonic = False
        radStraight02.Location = New System.Drawing.Point(14, 50) : radStraight02.Size = New System.Drawing.Size(445, 22)
        radStraight02.Checked = (s02.TrajectoryMode = "STRAIGHT")
        radStraight02.ForeColor = System.Drawing.Color.FromArgb(60, 70, 80)
        grpTraj02.Controls.Add(radStraight02)

        Dim lblCurve02 As New System.Windows.Forms.Label()
        lblCurve02.Text = "Độ uốn cánh cung (% Skid):"
        lblCurve02.Location = New System.Drawing.Point(14, 80) : lblCurve02.Size = New System.Drawing.Size(180, 20)
        grpTraj02.Controls.Add(lblCurve02)
        Dim numCurve02 As New System.Windows.Forms.NumericUpDown()
        numCurve02.Location = New System.Drawing.Point(200, 78) : numCurve02.Size = New System.Drawing.Size(95, 22)
        numCurve02.DecimalPlaces = 1 : numCurve02.Increment = 1.0D : numCurve02.Minimum = 0.0D : numCurve02.Maximum = 500.0D
        numCurve02.Value = CDec(s02.SwoopCurvature)
        grpTraj02.Controls.Add(numCurve02)

        Dim lblCurveInfo02 As New System.Windows.Forms.Label()
        lblCurveInfo02.Location = New System.Drawing.Point(302, 80) : lblCurveInfo02.Size = New System.Drawing.Size(160, 20)
        lblCurveInfo02.Font = New System.Drawing.Font("Segoe UI", 8.25!, FontStyle.Italic)
        lblCurveInfo02.ForeColor = System.Drawing.Color.FromArgb(20, 120, 60)
        grpTraj02.Controls.Add(lblCurveInfo02)

        Dim updateCurveLabel02 As Action = Sub()
            Dim cVal As Double = CDbl(numCurve02.Value)
            Dim estM As Double = (cVal * 0.015 * model.Diag) / 100.0
            lblCurveInfo02.Text = String.Format("≈ vồng ngang {0:F1}m", estM)
        End Sub
        AddHandler numCurve02.ValueChanged, Sub(s As Object, e As EventArgs) updateCurveLabel02()
        updateCurveLabel02()

        Dim grpParams02 As New System.Windows.Forms.GroupBox()
        grpParams02.Text = " 4. THÔNG SỐ CHUYỂN ĐỘNG CẢNH 2 "
        grpParams02.Location = New System.Drawing.Point(12, 362) : grpParams02.Size = New System.Drawing.Size(516, 370)
        grpParams02.BackColor = System.Drawing.Color.White
        page02.Controls.Add(grpParams02)

        Dim lblDur02 As New System.Windows.Forms.Label()
        lblDur02.Text = "Thời lượng bay lùi (giây):"
        lblDur02.Location = New System.Drawing.Point(16, 22) : lblDur02.Size = New System.Drawing.Size(220, 18)
        grpParams02.Controls.Add(lblDur02)
        Dim numDur02 As New System.Windows.Forms.NumericUpDown()
        numDur02.Location = New System.Drawing.Point(280, 20) : numDur02.Size = New System.Drawing.Size(120, 22)
        numDur02.DecimalPlaces = 1 : numDur02.Increment = 0.5D : numDur02.Minimum = 0.1D : numDur02.Maximum = 300.0D
        numDur02.Value = CDec(s02.DurationSeconds)
        grpParams02.Controls.Add(numDur02)

        Dim lblSpeed02 As New System.Windows.Forms.Label()
        lblSpeed02.Text = "Tốc độ bay (Hệ số Speed):"
        lblSpeed02.Location = New System.Drawing.Point(16, 50) : lblSpeed02.Size = New System.Drawing.Size(220, 18)
        grpParams02.Controls.Add(lblSpeed02)
        Dim numSpeed02 As New System.Windows.Forms.NumericUpDown()
        numSpeed02.Location = New System.Drawing.Point(280, 48) : numSpeed02.Size = New System.Drawing.Size(120, 22)
        numSpeed02.DecimalPlaces = 2 : numSpeed02.Increment = 0.1D : numSpeed02.Minimum = 0.01D : numSpeed02.Maximum = 50.0D
        numSpeed02.Value = CDec(s02.SpeedMultiplier)
        grpParams02.Controls.Add(numSpeed02)

        Dim lblSpeedInfo02 As New System.Windows.Forms.Label()
        lblSpeedInfo02.Location = New System.Drawing.Point(16, 74) : lblSpeedInfo02.Size = New System.Drawing.Size(440, 18)
        lblSpeedInfo02.Font = New System.Drawing.Font("Segoe UI", 8.25!, FontStyle.Italic)
        lblSpeedInfo02.ForeColor = System.Drawing.Color.FromArgb(20, 120, 60)
        grpParams02.Controls.Add(lblSpeedInfo02)

        Dim lblDistS02 As New System.Windows.Forms.Label()
        lblDistS02.Text = "Cự ly GẦN lúc bắt đầu (Fit View):"
        lblDistS02.Location = New System.Drawing.Point(16, 98) : lblDistS02.Size = New System.Drawing.Size(220, 18)
        grpParams02.Controls.Add(lblDistS02)
        Dim numDistS02 As New System.Windows.Forms.NumericUpDown()
        numDistS02.Location = New System.Drawing.Point(280, 96) : numDistS02.Size = New System.Drawing.Size(120, 22)
        numDistS02.DecimalPlaces = 2 : numDistS02.Increment = 0.05D : numDistS02.Minimum = 0.01D : numDistS02.Maximum = 50.0D
        numDistS02.Value = CDec(s02.StartDistanceScale)
        grpParams02.Controls.Add(numDistS02)

        Dim lblDistE02 As New System.Windows.Forms.Label()
        lblDistE02.Text = "Cự ly XA lúc kết thúc (x Model):"
        lblDistE02.Location = New System.Drawing.Point(16, 126) : lblDistE02.Size = New System.Drawing.Size(220, 18)
        grpParams02.Controls.Add(lblDistE02)
        Dim numDistE02 As New System.Windows.Forms.NumericUpDown()
        numDistE02.Location = New System.Drawing.Point(280, 124) : numDistE02.Size = New System.Drawing.Size(120, 22)
        numDistE02.DecimalPlaces = 2 : numDistE02.Increment = 0.2D : numDistE02.Minimum = 0.05D : numDistE02.Maximum = 100.0D
        numDistE02.Value = CDec(s02.EndDistanceScale)
        grpParams02.Controls.Add(numDistE02)

        Dim lblEasing02 As New System.Windows.Forms.Label()
        lblEasing02.Text = "Gia tốc tốc độ bay:"
        lblEasing02.Location = New System.Drawing.Point(16, 154) : lblEasing02.Size = New System.Drawing.Size(180, 18)
        grpParams02.Controls.Add(lblEasing02)
        Dim cboEasing02 As New System.Windows.Forms.ComboBox()
        cboEasing02.DropDownStyle = ComboBoxStyle.DropDownList
        cboEasing02.Location = New System.Drawing.Point(180, 152) : cboEasing02.Size = New System.Drawing.Size(320, 24)
        cboEasing02.Font = New System.Drawing.Font("Segoe UI", 8.5!, FontStyle.Bold)
        cboEasing02.ForeColor = System.Drawing.Color.FromArgb(20, 100, 50)
        cboEasing02.Items.Add("Chậm dần (Ease-Out) — Vút nhanh, hãm phanh êm [Khuyên]")
        cboEasing02.Items.Add("Nhanh dần (Ease-In) — Bắt đầu chậm, phóng vút ra xa")
        cboEasing02.Items.Add("Mượt 2 đầu (Ease-In-Out) — Êm đầu, nhanh giữa, êm cuối")
        cboEasing02.Items.Add("Đều đặn (Linear) — Tốc độ đều tắp từ đầu đến cuối")
        cboEasing02.SelectedIndex = If(s02.EasingMode = "EASE_IN", 1, If(s02.EasingMode = "EASE_IN_OUT", 2, If(s02.EasingMode = "LINEAR", 3, 0)))
        grpParams02.Controls.Add(cboEasing02)

        Dim lblBankS02 As New System.Windows.Forms.Label()
        lblBankS02.Text = "Độ nghiêng BẮT ĐẦU (độ):"
        lblBankS02.Location = New System.Drawing.Point(16, 186) : lblBankS02.Size = New System.Drawing.Size(220, 18)
        grpParams02.Controls.Add(lblBankS02)
        Dim numBankS02 As New System.Windows.Forms.NumericUpDown()
        numBankS02.Location = New System.Drawing.Point(280, 184) : numBankS02.Size = New System.Drawing.Size(120, 22)
        numBankS02.DecimalPlaces = 1 : numBankS02.Increment = 1.0D : numBankS02.Minimum = -89.0D : numBankS02.Maximum = 89.0D
        numBankS02.Value = CDec(s02.BankStart)
        grpParams02.Controls.Add(numBankS02)

        Dim lblBankE02 As New System.Windows.Forms.Label()
        lblBankE02.Text = "Độ nghiêng KẾT THÚC (độ):"
        lblBankE02.Location = New System.Drawing.Point(16, 214) : lblBankE02.Size = New System.Drawing.Size(220, 18)
        grpParams02.Controls.Add(lblBankE02)
        Dim numBankE02 As New System.Windows.Forms.NumericUpDown()
        numBankE02.Location = New System.Drawing.Point(280, 212) : numBankE02.Size = New System.Drawing.Size(120, 22)
        numBankE02.DecimalPlaces = 1 : numBankE02.Increment = 1.0D : numBankE02.Minimum = -89.0D : numBankE02.Maximum = 89.0D
        numBankE02.Value = CDec(s02.BankEnd)
        grpParams02.Controls.Add(numBankE02)

        Dim lblHold02 As New System.Windows.Forms.Label()
        lblHold02.Text = "Thời gian dừng ngắm ở xa (giây):"
        lblHold02.Location = New System.Drawing.Point(16, 242) : lblHold02.Size = New System.Drawing.Size(220, 18)
        grpParams02.Controls.Add(lblHold02)
        Dim numHold02 As New System.Windows.Forms.NumericUpDown()
        numHold02.Location = New System.Drawing.Point(280, 240) : numHold02.Size = New System.Drawing.Size(120, 22)
        numHold02.DecimalPlaces = 1 : numHold02.Increment = 0.5D : numHold02.Minimum = 0.0D : numHold02.Maximum = 120.0D
        numHold02.Value = CDec(s02.HoldSeconds)
        grpParams02.Controls.Add(numHold02)

        Dim updateSpeedLabel02 As Action = Sub()
            Dim dur As Double = CDbl(numDur02.Value)
            Dim spd As Double = CDbl(numSpeed02.Value)
            Dim hold As Double = CDbl(numHold02.Value)
            Dim actualT As Double = dur / Math.Max(0.05, spd)
            Dim totalT As Double = actualT + hold
            lblSpeedInfo02.Text = String.Format("▶ Bay lùi: {0:F1}s | Ngắm ở xa: {1:F1}s  ➔  Tổng chạy C2: {2:F1}s ({3:F2}x)", actualT, hold, totalT, spd)
        End Sub

        AddHandler numDur02.ValueChanged, Sub(s As Object, e As EventArgs) updateSpeedLabel02()
        AddHandler numSpeed02.ValueChanged, Sub(s As Object, e As EventArgs) updateSpeedLabel02()
        AddHandler numHold02.ValueChanged, Sub(s As Object, e As EventArgs) updateSpeedLabel02()
        updateSpeedLabel02()

        ' ======================================================================
        ' TAB 3: CẢNH 3 — ĐONG ĐƯA CON LẮC (PENDULUM SWAY AROUND HERO)
        ' ======================================================================
        Dim page03 As New System.Windows.Forms.TabPage()
        page03.Text = "🎭 CẢNH 3: ĐONG ĐƯA"
        page03.BackColor = System.Drawing.Color.FromArgb(248, 249, 250)
        page03.AutoScroll = True
        tabStudio.TabPages.Add(page03)

        ' Bento 1: Tiêu điểm con lắc (Vạn năng cho 100% mô hình + Nút Pick điểm)
        Dim grpTarget03 As New System.Windows.Forms.GroupBox()
        grpTarget03.Text = " 1. TIÊU ĐIỂM CON LẮC (MẶT TIỀN HOẶC GÓC 3/4) "
        grpTarget03.Location = New System.Drawing.Point(12, 10) : grpTarget03.Size = New System.Drawing.Size(516, 115)
        grpTarget03.BackColor = System.Drawing.Color.White
        page03.Controls.Add(grpTarget03)

        Dim lblTargetPrompt03 As New System.Windows.Forms.Label()
        lblTargetPrompt03.Text = "Phân vùng đong đưa:"
        lblTargetPrompt03.Location = New System.Drawing.Point(14, 25) : lblTargetPrompt03.Size = New System.Drawing.Size(130, 20)
        grpTarget03.Controls.Add(lblTargetPrompt03)
        Dim cboTarget03 As New System.Windows.Forms.ComboBox()
        cboTarget03.DropDownStyle = ComboBoxStyle.DropDownList
        cboTarget03.Location = New System.Drawing.Point(150, 22) : cboTarget03.Size = New System.Drawing.Size(350, 24)
        cboTarget03.Font = New System.Drawing.Font("Segoe UI", 8.5!, FontStyle.Bold)
        cboTarget03.ForeColor = System.Drawing.Color.FromArgb(20, 100, 50)
        cboTarget03.Items.Add("Góc 1: Trước - Trái (-X, -Z) [Bơm & Hông trái]")
        cboTarget03.Items.Add("Góc 2: Trước - Phải (+X, -Z) [Màng UF bên phải]")
        cboTarget03.Items.Add("Góc 3: Sau - Phải (+X, +Z) [Đường ống sau & Màng]")
        cboTarget03.Items.Add("Góc 4: Sau - Trái (-X, +Z) [Đường ống sau & Tủ điện]")
        cboTarget03.Items.Add("Mặt Trước Máy (Góc 1 ➔ Góc 2) [Khuyến nghị]")
        cboTarget03.Items.Add("Mặt Sau Máy (Góc 4 ➔ Góc 3)")
        cboTarget03.Items.Add("Tâm Toàn Bộ Skid Máy (Đại cảnh bao quát)")
        cboTarget03.Items.Add("📌 Điểm Theo Chi Tiết Đang Chọn (SelectSet)")
        cboTarget03.SelectedIndex = 0
        grpTarget03.Controls.Add(cboTarget03)

        Dim btnPick03 As New System.Windows.Forms.Button()
        btnPick03.Text = "📌 LẤY THEO CHI TIẾT ĐANG CHỌN (SELECTSET)"
        btnPick03.Location = New System.Drawing.Point(14, 52) : btnPick03.Size = New System.Drawing.Size(340, 25)
        btnPick03.BackColor = System.Drawing.Color.FromArgb(240, 246, 255)
        btnPick03.ForeColor = System.Drawing.Color.FromArgb(10, 80, 160)
        btnPick03.Font = New System.Drawing.Font("Segoe UI", 8.0!, FontStyle.Bold)
        btnPick03.FlatStyle = FlatStyle.Flat
        btnPick03.FlatAppearance.BorderColor = System.Drawing.Color.FromArgb(140, 180, 230)
        grpTarget03.Controls.Add(btnPick03)

        Dim lblTargetInfo03 As New System.Windows.Forms.Label()
        lblTargetInfo03.Location = New System.Drawing.Point(14, 82) : lblTargetInfo03.Size = New System.Drawing.Size(445, 25)
        lblTargetInfo03.Font = New System.Drawing.Font("Segoe UI", 8.5!, FontStyle.Italic)
        lblTargetInfo03.ForeColor = System.Drawing.Color.FromArgb(20, 120, 60)
        grpTarget03.Controls.Add(lblTargetInfo03)

        Dim updateTargetInfo03 As Action = Sub()
            Select Case cboTarget03.SelectedIndex
                Case 0
                    lblTargetInfo03.Text = "✔ Trục con lắc lấy tâm Góc 1 (Trước - Trái) quanh khu vực Bơm"
                Case 1
                    lblTargetInfo03.Text = "✔ Trục con lắc lấy tâm Góc 2 (Trước - Phải) quanh khu vực Màng"
                Case 2
                    lblTargetInfo03.Text = "✔ Trục con lắc lấy tâm Góc 3 (Sau - Phải) quanh đường ống sau & Màng"
                Case 3
                    lblTargetInfo03.Text = "✔ Trục con lắc lấy tâm Góc 4 (Sau - Trái) quanh tủ điện & ống kỹ thuật"
                Case 4
                    lblTargetInfo03.Text = "✔ Quét đong đưa dọc toàn bộ Mặt Tiền (Góc 1 Trước-Trái ➔ Góc 2)"
                Case 5
                    lblTargetInfo03.Text = "✔ Quét đong đưa dọc toàn bộ Mặt Sau (Góc 4 ➔ Góc 3)"
                Case 6
                    lblTargetInfo03.Text = "✔ Trục quay lấy tâm đại cảnh toàn bộ cụm skid"
                Case 7
                    If s03.CustomPickPoint IsNot Nothing Then
                        lblTargetInfo03.Text = String.Format("✔ Đã chọn điểm: (X:{0:F1}, Y:{1:F1}, Z:{2:F1})", s03.CustomPickPoint.X, s03.CustomPickPoint.Y, s03.CustomPickPoint.Z)
                    Else
                        lblTargetInfo03.Text = "ℹ Chọn 1 chi tiết trong Inventor rồi bấm 'LẤY THEO CHI TIẾT ĐANG CHỌN'"
                    End If
                Case Else
                    lblTargetInfo03.Text = "✔ Trục con lắc lấy tâm Góc 1 (Trước - Trái) quanh khu vực Bơm"
            End Select
        End Sub
        AddHandler cboTarget03.SelectedIndexChanged, Sub(s As Object, e As EventArgs) updateTargetInfo03()
        updateTargetInfo03()

        AddHandler btnPick03.Click, Sub(s As Object, e As EventArgs)
            Try
                Dim selectSet As SelectSet = oDoc.SelectSet
                If selectSet IsNot Nothing AndAlso selectSet.Count > 0 Then
                    Dim selectedObj As Object = selectSet.Item(1)
                    Dim pt As Vec3 = Nothing
                    Dim objName As String = "Chi tiết"
                    If TypeOf selectedObj Is ComponentOccurrence Then
                        Dim occ As ComponentOccurrence = CType(selectedObj, ComponentOccurrence)
                        Dim b As Box = occ.RangeBox
                        pt = New Vec3((b.MinPoint.X + b.MaxPoint.X) * 0.5, (b.MinPoint.Y + b.MaxPoint.Y) * 0.5, (b.MinPoint.Z + b.MaxPoint.Z) * 0.5)
                        objName = occ.Name
                    Else
                        Try
                            Dim b As Box = CallByName(selectedObj, "RangeBox", CallType.Get)
                            pt = New Vec3((b.MinPoint.X + b.MaxPoint.X) * 0.5, (b.MinPoint.Y + b.MaxPoint.Y) * 0.5, (b.MinPoint.Z + b.MaxPoint.Z) * 0.5)
                        Catch
                        End Try
                    End If
                    If pt IsNot Nothing Then
                        s03.CustomPickPoint = pt
                        cboTarget03.SelectedIndex = 7
                        lblTargetInfo03.Text = String.Format("✔ Đã lấy tâm '{0}': (X:{1:F1}, Y:{2:F1}, Z:{3:F1})", objName, pt.X, pt.Y, pt.Z)
                    Else
                        MessageBox.Show("Không lấy được tọa độ RangeBox của đối tượng đang chọn.", "Thông báo", MessageBoxButtons.OK, MessageBoxIcon.Information)
                    End If
                Else
                    MessageBox.Show("Chưa có linh kiện nào được chọn trong Inventor." & vbCrLf & vbCrLf & _
                                    "👉 Hướng dẫn:" & vbCrLf & _
                                    "1. Hãy nhấp chọn 1 chi tiết/linh kiện trên Cây mô hình (Model Browser) hoặc trên mô hình." & vbCrLf & _
                                    "2. Sau đó bấm lại nút này để lấy tọa độ làm tâm con lắc.", _
                                    "Chưa chọn linh kiện", MessageBoxButtons.OK, MessageBoxIcon.Information)
                End If
            Catch ex As Exception
                MessageBox.Show("Lỗi lấy chi tiết: " & ex.Message, "Lỗi", MessageBoxButtons.OK, MessageBoxIcon.Warning)
            End Try
        End Sub

        ' Bento 2: Cao độ góc nhìn 3/4
        Dim grpAngle03 As New System.Windows.Forms.GroupBox()
        grpAngle03.Text = " 2. CAO ĐỘ GÓC NHÌN CON LẮC (TRÊN / DƯỚI / NGANG) "
        grpAngle03.Location = New System.Drawing.Point(12, 132) : grpAngle03.Size = New System.Drawing.Size(516, 115)
        grpAngle03.BackColor = System.Drawing.Color.White
        page03.Controls.Add(grpAngle03)

        Dim radBottom03 As New System.Windows.Forms.RadioButton()
        radBottom03.Text = "▼ 3/4 DƯỚI   — Hất từ bệ thép lên bề thế, uy lực"
        radBottom03.UseMnemonic = False
        radBottom03.Location = New System.Drawing.Point(14, 22) : radBottom03.Size = New System.Drawing.Size(445, 22)
        radBottom03.Font = New System.Drawing.Font("Segoe UI", 9.0!, FontStyle.Bold)
        radBottom03.ForeColor = System.Drawing.Color.FromArgb(140, 60, 10)
        grpAngle03.Controls.Add(radBottom03)

        Dim radTop03 As New System.Windows.Forms.RadioButton()
        radTop03.Text = "▲ 3/4 TRÊN   — Nhìn từ trên cao xuống bao quát đầu bơm/van [Khuyến nghị]"
        radTop03.UseMnemonic = False
        radTop03.Location = New System.Drawing.Point(14, 52) : radTop03.Size = New System.Drawing.Size(445, 22)
        radTop03.Checked = True
        radTop03.Font = New System.Drawing.Font("Segoe UI", 9.0!, FontStyle.Bold)
        radTop03.ForeColor = System.Drawing.Color.FromArgb(20, 100, 50)
        grpAngle03.Controls.Add(radTop03)

        Dim radLevel03 As New System.Windows.Forms.RadioButton()
        radLevel03.Text = "■ 3/4 NGANG  — Ngang tầm mắt chuẩn kỹ thuật"
        radLevel03.UseMnemonic = False
        radLevel03.Location = New System.Drawing.Point(14, 82) : radLevel03.Size = New System.Drawing.Size(445, 22)
        radLevel03.ForeColor = System.Drawing.Color.FromArgb(60, 70, 80)
        grpAngle03.Controls.Add(radLevel03)

        ' Bento 3: Cấu hình Đong Đưa Con Lắc
        Dim grpSway03 As New System.Windows.Forms.GroupBox()
        grpSway03.Text = " 3. CẤU HÌNH ĐONG ĐƯA CON LẮC (PENDULUM SWAY) "
        grpSway03.Location = New System.Drawing.Point(12, 254) : grpSway03.Size = New System.Drawing.Size(516, 145)
        grpSway03.BackColor = System.Drawing.Color.White
        page03.Controls.Add(grpSway03)

        Dim lblCycle03 As New System.Windows.Forms.Label()
        lblCycle03.Text = "Nhịp đảo hướng con lắc:"
        lblCycle03.Location = New System.Drawing.Point(14, 25) : lblCycle03.Size = New System.Drawing.Size(150, 20)
        grpSway03.Controls.Add(lblCycle03)
        Dim cboCycle03 As New System.Windows.Forms.ComboBox()
        cboCycle03.DropDownStyle = ComboBoxStyle.DropDownList
        cboCycle03.Location = New System.Drawing.Point(166, 22) : cboCycle03.Size = New System.Drawing.Size(334, 24)
        cboCycle03.Font = New System.Drawing.Font("Segoe UI", 8.5!, FontStyle.Bold)
        cboCycle03.ForeColor = System.Drawing.Color.FromArgb(20, 100, 50)
        cboCycle03.Items.Add("1 Chu kỳ đầy đủ (Trái ➔ Cận Hero ➔ Phải ➔ Về Trái) [Khuyên]")
        cboCycle03.Items.Add("Nửa chu kỳ (Trái ➔ Cận Hero ➔ Vút sang Phải)")
        cboCycle03.Items.Add("2 Chu kỳ (Đong đưa 2 vòng qua lại)")
        cboCycle03.SelectedIndex = 0
        grpSway03.Controls.Add(cboCycle03)

        Dim lblSway03 As New System.Windows.Forms.Label()
        lblSway03.Text = "Độ đong đưa (% Sway):"
        lblSway03.Location = New System.Drawing.Point(14, 55) : lblSway03.Size = New System.Drawing.Size(180, 20)
        grpSway03.Controls.Add(lblSway03)
        Dim numSway03 As New System.Windows.Forms.NumericUpDown()
        numSway03.Location = New System.Drawing.Point(200, 53) : numSway03.Size = New System.Drawing.Size(95, 22)
        numSway03.DecimalPlaces = 1 : numSway03.Increment = 5.0D : numSway03.Minimum = 0.0D : numSway03.Maximum = 200.0D
        numSway03.Value = CDec(s03.SwayPercent)
        grpSway03.Controls.Add(numSway03)

        Dim lblSwayInfo03 As New System.Windows.Forms.Label()
        lblSwayInfo03.Text = "(55% = Cinematic tự nhiên)"
        lblSwayInfo03.Location = New System.Drawing.Point(302, 55) : lblSwayInfo03.Size = New System.Drawing.Size(160, 20)
        lblSwayInfo03.Font = New System.Drawing.Font("Segoe UI", 8.0!, FontStyle.Italic)
        lblSwayInfo03.ForeColor = System.Drawing.Color.FromArgb(20, 120, 60)
        grpSway03.Controls.Add(lblSwayInfo03)

        Dim lblNearDist03 As New System.Windows.Forms.Label()
        lblNearDist03.Text = "Cự ly ÉP SÁT Hero (Near):"
        lblNearDist03.Location = New System.Drawing.Point(14, 85) : lblNearDist03.Size = New System.Drawing.Size(180, 20)
        grpSway03.Controls.Add(lblNearDist03)
        Dim numNearDist03 As New System.Windows.Forms.NumericUpDown()
        numNearDist03.Location = New System.Drawing.Point(200, 83) : numNearDist03.Size = New System.Drawing.Size(95, 22)
        numNearDist03.DecimalPlaces = 2 : numNearDist03.Increment = 0.05D : numNearDist03.Minimum = 0.01D : numNearDist03.Maximum = 20.0D
        numNearDist03.Value = CDec(s03.NearDistanceScale)
        grpSway03.Controls.Add(numNearDist03)

        Dim lblFarDist03 As New System.Windows.Forms.Label()
        lblFarDist03.Text = "Cự ly DÃN XA mạn sườn (Far):"
        lblFarDist03.Location = New System.Drawing.Point(14, 115) : lblFarDist03.Size = New System.Drawing.Size(180, 20)
        grpSway03.Controls.Add(lblFarDist03)
        Dim numFarDist03 As New System.Windows.Forms.NumericUpDown()
        numFarDist03.Location = New System.Drawing.Point(200, 113) : numFarDist03.Size = New System.Drawing.Size(95, 22)
        numFarDist03.DecimalPlaces = 2 : numFarDist03.Increment = 0.05D : numFarDist03.Minimum = 0.05D : numFarDist03.Maximum = 50.0D
        numFarDist03.Value = CDec(s03.FarDistanceScale)
        grpSway03.Controls.Add(numFarDist03)

        ' Bento 4: Thông số chuyển động Cảnh 3
        Dim grpParams03 As New System.Windows.Forms.GroupBox()
        grpParams03.Text = " 4. THÔNG SỐ CHUYỂN ĐỘNG && GIA TỐC CẢNH 3 "
        grpParams03.Location = New System.Drawing.Point(12, 406) : grpParams03.Size = New System.Drawing.Size(516, 250)
        grpParams03.BackColor = System.Drawing.Color.White
        page03.Controls.Add(grpParams03)

        Dim lblDur03 As New System.Windows.Forms.Label()
        lblDur03.Text = "Thời lượng chuyển động (giây):"
        lblDur03.Location = New System.Drawing.Point(16, 22) : lblDur03.Size = New System.Drawing.Size(220, 18)
        grpParams03.Controls.Add(lblDur03)
        Dim numDur03 As New System.Windows.Forms.NumericUpDown()
        numDur03.Location = New System.Drawing.Point(280, 20) : numDur03.Size = New System.Drawing.Size(120, 22)
        numDur03.DecimalPlaces = 1 : numDur03.Increment = 0.5D : numDur03.Minimum = 0.1D : numDur03.Maximum = 300.0D
        numDur03.Value = CDec(s03.DurationSeconds)
        grpParams03.Controls.Add(numDur03)

        Dim lblSpeed03 As New System.Windows.Forms.Label()
        lblSpeed03.Text = "Tốc độ bay (Hệ số Speed):"
        lblSpeed03.Location = New System.Drawing.Point(16, 50) : lblSpeed03.Size = New System.Drawing.Size(220, 18)
        grpParams03.Controls.Add(lblSpeed03)
        Dim numSpeed03 As New System.Windows.Forms.NumericUpDown()
        numSpeed03.Location = New System.Drawing.Point(280, 48) : numSpeed03.Size = New System.Drawing.Size(120, 22)
        numSpeed03.DecimalPlaces = 2 : numSpeed03.Increment = 0.1D : numSpeed03.Minimum = 0.01D : numSpeed03.Maximum = 50.0D
        numSpeed03.Value = CDec(s03.SpeedMultiplier)
        grpParams03.Controls.Add(numSpeed03)

        Dim lblSpeedInfo03 As New System.Windows.Forms.Label()
        lblSpeedInfo03.Location = New System.Drawing.Point(16, 74) : lblSpeedInfo03.Size = New System.Drawing.Size(440, 18)
        lblSpeedInfo03.Font = New System.Drawing.Font("Segoe UI", 8.25!, FontStyle.Italic)
        lblSpeedInfo03.ForeColor = System.Drawing.Color.FromArgb(20, 120, 60)
        grpParams03.Controls.Add(lblSpeedInfo03)

        Dim lblEasing03 As New System.Windows.Forms.Label()
        lblEasing03.Text = "Gia tốc tốc độ bay:"
        lblEasing03.Location = New System.Drawing.Point(16, 98) : lblEasing03.Size = New System.Drawing.Size(135, 18)
        grpParams03.Controls.Add(lblEasing03)
        Dim cboEasing03 As New System.Windows.Forms.ComboBox()
        cboEasing03.DropDownStyle = ComboBoxStyle.DropDownList
        cboEasing03.Location = New System.Drawing.Point(155, 96) : cboEasing03.Size = New System.Drawing.Size(345, 24)
        cboEasing03.Font = New System.Drawing.Font("Segoe UI", 8.5!, FontStyle.Bold)
        cboEasing03.ForeColor = System.Drawing.Color.FromArgb(20, 100, 50)
        cboEasing03.Items.Add("Mượt 2 đầu (Ease-In-Out) — Chuẩn con lắc [Khuyên]")
        cboEasing03.Items.Add("Chậm dần (Ease-Out) — Lao nhanh vào, hãm phanh êm")
        cboEasing03.Items.Add("Nhanh dần (Ease-In) — Bắt đầu chậm, phóng vút ra xa")
        cboEasing03.Items.Add("Đều đặn (Linear) — Vận tốc đều tắp từ đầu đến cuối")
        cboEasing03.SelectedIndex = 0
        grpParams03.Controls.Add(cboEasing03)

        Dim lblBankS03 As New System.Windows.Forms.Label()
        lblBankS03.Text = "Độ nghiêng BẮT ĐẦU (độ):"
        lblBankS03.Location = New System.Drawing.Point(16, 130) : lblBankS03.Size = New System.Drawing.Size(220, 18)
        grpParams03.Controls.Add(lblBankS03)
        Dim numBankS03 As New System.Windows.Forms.NumericUpDown()
        numBankS03.Location = New System.Drawing.Point(280, 128) : numBankS03.Size = New System.Drawing.Size(120, 22)
        numBankS03.DecimalPlaces = 1 : numBankS03.Increment = 1.0D : numBankS03.Minimum = -89.0D : numBankS03.Maximum = 89.0D
        numBankS03.Value = CDec(s03.BankStart)
        grpParams03.Controls.Add(numBankS03)

        Dim lblBankE03 As New System.Windows.Forms.Label()
        lblBankE03.Text = "Độ nghiêng KẾT THÚC (độ):"
        lblBankE03.Location = New System.Drawing.Point(16, 158) : lblBankE03.Size = New System.Drawing.Size(220, 18)
        grpParams03.Controls.Add(lblBankE03)
        Dim numBankE03 As New System.Windows.Forms.NumericUpDown()
        numBankE03.Location = New System.Drawing.Point(280, 156) : numBankE03.Size = New System.Drawing.Size(120, 22)
        numBankE03.DecimalPlaces = 1 : numBankE03.Increment = 1.0D : numBankE03.Minimum = -89.0D : numBankE03.Maximum = 89.0D
        numBankE03.Value = CDec(s03.BankEnd)
        grpParams03.Controls.Add(numBankE03)

        Dim lblBob03 As New System.Windows.Forms.Label()
        lblBob03.Text = "Nhấp nhô cao độ (% Chiều cao):"
        lblBob03.Location = New System.Drawing.Point(16, 186) : lblBob03.Size = New System.Drawing.Size(220, 18)
        grpParams03.Controls.Add(lblBob03)
        Dim numBob03 As New System.Windows.Forms.NumericUpDown()
        numBob03.Location = New System.Drawing.Point(280, 184) : numBob03.Size = New System.Drawing.Size(120, 22)
        numBob03.DecimalPlaces = 1 : numBob03.Increment = 1.0D : numBob03.Minimum = 0.0D : numBob03.Maximum = 100.0D
        numBob03.Value = CDec(s03.VerticalBobPercent)
        grpParams03.Controls.Add(numBob03)

        Dim lblHold03 As New System.Windows.Forms.Label()
        lblHold03.Text = "Thời gian dừng ngắm kết thúc (giây):"
        lblHold03.Location = New System.Drawing.Point(16, 214) : lblHold03.Size = New System.Drawing.Size(220, 18)
        grpParams03.Controls.Add(lblHold03)
        Dim numHold03 As New System.Windows.Forms.NumericUpDown()
        numHold03.Location = New System.Drawing.Point(280, 212) : numHold03.Size = New System.Drawing.Size(120, 22)
        numHold03.DecimalPlaces = 1 : numHold03.Increment = 0.5D : numHold03.Minimum = 0.0D : numHold03.Maximum = 120.0D
        numHold03.Value = CDec(s03.HoldSeconds)
        grpParams03.Controls.Add(numHold03)

        Dim updateSpeedLabel03 As Action = Sub()
            Dim dur As Double = CDbl(numDur03.Value)
            Dim spd As Double = CDbl(numSpeed03.Value)
            Dim hold As Double = CDbl(numHold03.Value)
            Dim actualT As Double = dur / Math.Max(0.05, spd)
            Dim totalT As Double = actualT + hold
            lblSpeedInfo03.Text = String.Format("▶ Đong đưa: {0:F1}s | Dừng ngắm: {1:F1}s  ➔  Tổng chạy C3: {2:F1}s ({3:F2}x)", actualT, hold, totalT, spd)
        End Sub
        AddHandler numDur03.ValueChanged, Sub(s As Object, e As EventArgs) updateSpeedLabel03()
        AddHandler numSpeed03.ValueChanged, Sub(s As Object, e As EventArgs) updateSpeedLabel03()
        AddHandler numHold03.ValueChanged, Sub(s As Object, e As EventArgs) updateSpeedLabel03()
        updateSpeedLabel03()

        ' ======================================================================
        ' TAB 4: CẢNH 4 — POLYGON SNAP-ORBIT & MULTI-POINT MACRO ZOOM
        ' ======================================================================
        Dim page04 As New System.Windows.Forms.TabPage()
        page04.Text = "⚡ CẢNH 4: POLYGON ZOOM"
        page04.BackColor = System.Drawing.Color.FromArgb(248, 249, 250)
        page04.AutoScroll = True
        tabStudio.TabPages.Add(page04)

        ' Bento 1: Cấu hình Đa Giác & Điểm Phóng Zoom
        Dim grpPoly04 As New System.Windows.Forms.GroupBox()
        grpPoly04.Text = " 1. CẤU HÌNH ĐA GIÁC && CÁC ĐIỂM SOI (POLYGON && HERO POINTS) "
        grpPoly04.Location = New System.Drawing.Point(12, 10) : grpPoly04.Size = New System.Drawing.Size(516, 195)
        grpPoly04.BackColor = System.Drawing.Color.White
        page04.Controls.Add(grpPoly04)

        Dim lblMode04 As New System.Windows.Forms.Label()
        lblMode04.Text = "Lộ trình phóng Zoom:"
        lblMode04.Location = New System.Drawing.Point(14, 22) : lblMode04.Size = New System.Drawing.Size(140, 20)
        grpPoly04.Controls.Add(lblMode04)

        Dim cboMode04 As New System.Windows.Forms.ComboBox()
        cboMode04.DropDownStyle = ComboBoxStyle.DropDownList
        cboMode04.Location = New System.Drawing.Point(160, 19) : cboMode04.Size = New System.Drawing.Size(340, 24)
        cboMode04.Font = New System.Drawing.Font("Segoe UI", 8.5!, FontStyle.Bold)
        cboMode04.ForeColor = System.Drawing.Color.FromArgb(20, 100, 50)
        cboMode04.Items.Add("4 Điểm TVC High-Tech (Bơm ➔ Đồng hồ ➔ Màng ➔ Tủ) [Khuyên]")
        cboMode04.Items.Add("3 Điểm Siêu Nhanh (Bơm ➔ Màng RO/UF ➔ Tủ điện)")
        cboMode04.Items.Add("Tự chọn qua SelectSet (Click chi tiết trong Inventor)")
        cboMode04.SelectedIndex = If(s04.CustomPickPoints.Count > 0, 2, 0)
        grpPoly04.Controls.Add(cboMode04)

        ' Nút 1: Click trực tiếp trên 3D (Tự đóng Form -> Click Inventor -> Mở lại)
        Dim btnInteractivePick04 As New System.Windows.Forms.Button()
        btnInteractivePick04.Text = "► CLICK CHỌN TRỰC TIẾP TRÊN 3D"
        btnInteractivePick04.Location = New System.Drawing.Point(14, 50) : btnInteractivePick04.Size = New System.Drawing.Size(240, 32)
        btnInteractivePick04.BackColor = System.Drawing.Color.FromArgb(16, 110, 60)
        btnInteractivePick04.ForeColor = System.Drawing.Color.White
        btnInteractivePick04.FlatStyle = FlatStyle.Flat
        btnInteractivePick04.Font = New System.Drawing.Font("Segoe UI", 9.0!, FontStyle.Bold)
        grpPoly04.Controls.Add(btnInteractivePick04)

        ' Nút 2: Nạp hàng loạt các chi tiết đang chọn (SelectSet)
        Dim btnSelectSetPick04 As New System.Windows.Forms.Button()
        btnSelectSetPick04.Text = "✔ NẠP CHI TIẾT ĐANG CHỌN"
        btnSelectSetPick04.Location = New System.Drawing.Point(260, 50) : btnSelectSetPick04.Size = New System.Drawing.Size(155, 32)
        btnSelectSetPick04.BackColor = System.Drawing.Color.FromArgb(240, 248, 255)
        btnSelectSetPick04.ForeColor = System.Drawing.Color.FromArgb(10, 80, 160)
        btnSelectSetPick04.FlatStyle = FlatStyle.Flat
        btnSelectSetPick04.Font = New System.Drawing.Font("Segoe UI", 8.25!, FontStyle.Bold)
        grpPoly04.Controls.Add(btnSelectSetPick04)

        ' Nút 3: Xóa điểm
        Dim btnClear04 As New System.Windows.Forms.Button()
        btnClear04.Text = "✕ XÓA ĐIỂM"
        btnClear04.Location = New System.Drawing.Point(420, 50) : btnClear04.Size = New System.Drawing.Size(80, 32)
        btnClear04.BackColor = System.Drawing.Color.FromArgb(255, 240, 240)
        btnClear04.ForeColor = System.Drawing.Color.FromArgb(180, 40, 20)
        btnClear04.FlatStyle = FlatStyle.Flat
        btnClear04.Font = New System.Drawing.Font("Segoe UI", 8.25!, FontStyle.Bold)
        grpPoly04.Controls.Add(btnClear04)

        ' Nút 4: Lưu điểm vĩnh viễn (Save Points)
        Dim btnSavePoints04 As New System.Windows.Forms.Button()
        btnSavePoints04.Text = "LƯU CÁC ĐIỂM ĐÃ CHỌN"
        btnSavePoints04.Location = New System.Drawing.Point(14, 88) : btnSavePoints04.Size = New System.Drawing.Size(240, 28)
        btnSavePoints04.BackColor = System.Drawing.Color.FromArgb(245, 250, 245)
        btnSavePoints04.ForeColor = System.Drawing.Color.FromArgb(20, 120, 50)
        btnSavePoints04.FlatStyle = FlatStyle.Flat
        btnSavePoints04.Font = New System.Drawing.Font("Segoe UI", 8.5!, FontStyle.Bold)
        grpPoly04.Controls.Add(btnSavePoints04)

        ' Nút 5: Nạp lại điểm đã lưu (Load Points)
        Dim btnLoadPoints04 As New System.Windows.Forms.Button()
        btnLoadPoints04.Text = "NẠP LẠI ĐIỂM ĐÃ LƯU"
        btnLoadPoints04.Location = New System.Drawing.Point(260, 88) : btnLoadPoints04.Size = New System.Drawing.Size(240, 28)
        btnLoadPoints04.BackColor = System.Drawing.Color.FromArgb(245, 248, 255)
        btnLoadPoints04.ForeColor = System.Drawing.Color.FromArgb(20, 70, 150)
        btnLoadPoints04.FlatStyle = FlatStyle.Flat
        btnLoadPoints04.Font = New System.Drawing.Font("Segoe UI", 8.5!, FontStyle.Bold)
        grpPoly04.Controls.Add(btnLoadPoints04)

        Dim lblPolyStatus04 As New System.Windows.Forms.Label()
        If s04.CustomPickPoints.Count > 0 Then
            lblPolyStatus04.Text = String.Format("✔ Đã nạp {0} điểm: {1}", s04.CustomPickPoints.Count, String.Join(" ➔ ", customPointNames.ToArray()))
            lblPolyStatus04.ForeColor = System.Drawing.Color.FromArgb(10, 80, 160)
        Else
            lblPolyStatus04.Text = "✔ 4 Đỉnh đa giác quét trọn 4 mặt: Bơm ➔ Đồng hồ ➔ Màng ➔ Tủ điện"
            lblPolyStatus04.ForeColor = System.Drawing.Color.FromArgb(20, 120, 50)
        End If
        lblPolyStatus04.Font = New System.Drawing.Font("Segoe UI", 8.25!, FontStyle.Italic)
        lblPolyStatus04.Location = New System.Drawing.Point(14, 122) : lblPolyStatus04.Size = New System.Drawing.Size(485, 30)
        grpPoly04.Controls.Add(lblPolyStatus04)

        ' Chọn Hướng tiếp cận soi chi tiết
        Dim lblApproach04 As New System.Windows.Forms.Label()
        lblApproach04.Text = "Hướng Tiếp Cận Soi Chi Tiết:"
        lblApproach04.Location = New System.Drawing.Point(14, 158) : lblApproach04.Size = New System.Drawing.Size(180, 20)
        grpPoly04.Controls.Add(lblApproach04)

        Dim cboApproach04 As New System.Windows.Forms.ComboBox()
        cboApproach04.DropDownStyle = ComboBoxStyle.DropDownList
        cboApproach04.Location = New System.Drawing.Point(200, 155) : cboApproach04.Size = New System.Drawing.Size(300, 24)
        cboApproach04.Font = New System.Drawing.Font("Segoe UI", 8.25!, FontStyle.Bold)
        cboApproach04.ForeColor = System.Drawing.Color.FromArgb(20, 100, 50)
        cboApproach04.Items.Add("Tự Động Theo Mặt Ngoài Máy (Auto Exterior) [Khuyên dùng]")
        cboApproach04.Items.Add("Theo Góc Nhìn Lúc Click Chọn / Màn Hình (Recorded View)")
        cboApproach04.Items.Add("Góc 3/4 Mặt Trước - Trái (-X, -Z Isometric)")
        cboApproach04.Items.Add("Góc 3/4 Mặt Trước - Phải (+X, -Z Isometric)")
        cboApproach04.Items.Add("Trực Diện Mặt Trước (Front Direct Look)")
        cboApproach04.Items.Add("Từ Trên Cao Nhìn Xuống (Top-Down 45° Angle)")
        cboApproach04.SelectedIndex = 1
        grpPoly04.Controls.Add(cboApproach04)

        ' Xử lý nút Click trực tiếp trên 3D
        AddHandler btnInteractivePick04.Click, Sub(s As Object, e As EventArgs)
            activeTabIndex = 3
            formPendingAction = "INTERACTIVE_PICK"
            form.Close()
        End Sub

        ' Xử lý nút Nạp từ SelectSet (bóc tách đa tầng thông minh)
        AddHandler btnSelectSetPick04.Click, Sub(s As Object, e As EventArgs)
            Dim selSet As SelectSet = oDoc.SelectSet
            If selSet IsNot Nothing AndAlso selSet.Count > 0 Then
                Dim addedCount As Integer = 0
                For i As Integer = 1 To selSet.Count
                    Dim obj As Object = selSet.Item(i)
                    Dim pt As Vec3 = Nothing
                    Dim objName As String = "Chi tiết " & (s04.CustomPickPoints.Count + 1).ToString()

                    If TypeOf obj Is ComponentOccurrence Then
                        Dim occ As ComponentOccurrence = CType(obj, ComponentOccurrence)
                        Dim b As Box = occ.RangeBox
                        pt = New Vec3((b.MinPoint.X + b.MaxPoint.X) * 0.5, (b.MinPoint.Y + b.MaxPoint.Y) * 0.5, (b.MinPoint.Z + b.MaxPoint.Z) * 0.5)
                        objName = occ.Name
                    Else
                        Try
                            Dim occ As ComponentOccurrence = CallByName(obj, "ContainingOccurrence", CallType.Get)
                            If occ IsNot Nothing Then
                                Dim b As Box = occ.RangeBox
                                pt = New Vec3((b.MinPoint.X + b.MaxPoint.X) * 0.5, (b.MinPoint.Y + b.MaxPoint.Y) * 0.5, (b.MinPoint.Z + b.MaxPoint.Z) * 0.5)
                                objName = occ.Name
                            End If
                        Catch
                        End Try

                        If pt Is Nothing Then
                            Try
                                Dim b As Box = CallByName(obj, "RangeBox", CallType.Get)
                                pt = New Vec3((b.MinPoint.X + b.MaxPoint.X) * 0.5, (b.MinPoint.Y + b.MaxPoint.Y) * 0.5, (b.MinPoint.Z + b.MaxPoint.Z) * 0.5)
                            Catch
                            End Try
                        End If
                    End If

                    If pt IsNot Nothing Then
                        s04.CustomPickPoints.Add(pt)
                        Dim oCamNow As Inventor.Camera = oApp.ActiveView.Camera
                        Dim curViewVec As Vec3 = (New Vec3(oCamNow.Eye.X, oCamNow.Eye.Y, oCamNow.Eye.Z) - New Vec3(oCamNow.Target.X, oCamNow.Target.Y, oCamNow.Target.Z)).Normalize()
                        If curViewVec.Length() < 1E-5 Then curViewVec = New Vec3(-0.7071, 0.5, -0.7071).Normalize()
                        s04.CustomApproachVectors.Add(curViewVec)
                        customPointNames.Add(objName)
                        addedCount += 1
                    End If
                Next

                If addedCount > 0 Then
                    s04.PointsMode = "CUSTOM_PICK"
                    cboMode04.SelectedIndex = 2
                    lblPolyStatus04.Text = String.Format("✔ Đã nạp {0} điểm: {1}", s04.CustomPickPoints.Count, String.Join(" ➔ ", customPointNames.ToArray()))
                    lblPolyStatus04.ForeColor = System.Drawing.Color.FromArgb(10, 80, 160)
                    ' Tự động lưu vĩnh viễn (Auto-Save)
                    SavePointsToStorage(oDoc, s04.CustomPickPoints, s04.CustomApproachVectors, customPointNames)
                End If
            Else
                MessageBox.Show("Chưa có chi tiết nào được chọn trong Inventor!" & vbCrLf & vbCrLf & _
                                "👉 Cách 1 (Khuyên dùng): Bấm nút màu xanh đậm '🖱️ CLICK CHỌN TRỰC TIẾP TRÊN 3D' để click thẳng vào mô hình." & vbCrLf & _
                                "👉 Cách 2: Chọn trước các chi tiết trên màn hình Inventor rồi bấm lại nút này.", "WT3D Chọn Điểm", MessageBoxButtons.OK, MessageBoxIcon.Information)
            End If
        End Sub


        ' Xử lý nút Lưu điểm chủ động
        AddHandler btnSavePoints04.Click, Sub(s As Object, e As EventArgs)
            If s04.CustomPickPoints.Count > 0 Then
                SavePointsToStorage(oDoc, s04.CustomPickPoints, s04.CustomApproachVectors, customPointNames)
                MessageBox.Show(String.Format("✔ Đã lưu thành công {0} điểm vào file mô hình ({1}) và file sao lưu dự phòng!", s04.CustomPickPoints.Count, oDoc.DisplayName), "WT3D Lưu Điểm Thành Công", MessageBoxButtons.OK, MessageBoxIcon.Information)
            Else
                MessageBox.Show("Chưa có điểm nào để lưu. Vui lòng bấm '🎯 CLICK CHỌN TRỰC TIẾP TRÊN 3D' hoặc '✔ NẠP CHI TIẾT ĐANG CHỌN' trước.", "Thông Báo", MessageBoxButtons.OK, MessageBoxIcon.Warning)
            End If
        End Sub

        ' Xử lý nút Nạp lại điểm đã lưu
        AddHandler btnLoadPoints04.Click, Sub(s As Object, e As EventArgs)
            Dim loadedPts As List(Of Vec3) = Nothing
            Dim loadedDirs As List(Of Vec3) = Nothing
            Dim loadedNames As List(Of String) = Nothing
            If LoadPointsFromStorage(oDoc, loadedPts, loadedDirs, loadedNames) AndAlso loadedPts.Count > 0 Then
                s04.CustomPickPoints = loadedPts
                s04.CustomApproachVectors = loadedDirs
                customPointNames = loadedNames
                s04.PointsMode = "CUSTOM_PICK"
                cboMode04.SelectedIndex = 2
                lblPolyStatus04.Text = String.Format("✔ Đã nạp lại {0} điểm đã lưu: {1}", s04.CustomPickPoints.Count, String.Join(" ➔ ", customPointNames.ToArray()))
                lblPolyStatus04.ForeColor = System.Drawing.Color.FromArgb(10, 80, 160)
                MessageBox.Show(String.Format("✔ Đã nạp lại thành công {0} điểm đã lưu!", s04.CustomPickPoints.Count), "WT3D Nạp Điểm Thành Công", MessageBoxButtons.OK, MessageBoxIcon.Information)
            Else
                MessageBox.Show("Không tìm thấy dữ liệu điểm đã lưu cho mô hình này.", "Thông Báo", MessageBoxButtons.OK, MessageBoxIcon.Information)
            End If
        End Sub

        ' Xử lý nút Xóa điểm
        AddHandler btnClear04.Click, Sub(s As Object, e As EventArgs)
            s04.CustomPickPoints.Clear()
            s04.CustomApproachVectors.Clear()
            customPointNames.Clear()
            cboMode04.SelectedIndex = 0
            lblPolyStatus04.Text = "✔ Đã xóa điểm. Trở về mặc định 4 Điểm TVC High-Tech."
            lblPolyStatus04.ForeColor = System.Drawing.Color.FromArgb(20, 120, 50)
        End Sub

        ' Bento 2: Thông số Phóng Zoom & Góc Ống Kính
        Dim grpZoom04 As New System.Windows.Forms.GroupBox()
        grpZoom04.Text = " 2. THÔNG SỐ PHÓNG ZOOM && GÓC ỐNG KÍNH (ZOOM PUNCH && FOV) "
        grpZoom04.Location = New System.Drawing.Point(12, 213) : grpZoom04.Size = New System.Drawing.Size(516, 140)
        grpZoom04.BackColor = System.Drawing.Color.White
        page04.Controls.Add(grpZoom04)

        Dim lblDolly04 As New System.Windows.Forms.Label()
        lblDolly04.Text = "Cự ly ÉP SÁT khi Zoom (Near):"
        lblDolly04.Location = New System.Drawing.Point(14, 22) : lblDolly04.Size = New System.Drawing.Size(200, 20)
        grpZoom04.Controls.Add(lblDolly04)
        Dim numDolly04 As New System.Windows.Forms.NumericUpDown()
        numDolly04.Location = New System.Drawing.Point(220, 20) : numDolly04.Size = New System.Drawing.Size(95, 22)
        numDolly04.DecimalPlaces = 2 : numDolly04.Increment = 0.05D : numDolly04.Minimum = 0.01D : numDolly04.Maximum = 30.0D
        numDolly04.Value = CDec(s04.ZoomDollyScale)
        grpZoom04.Controls.Add(numDolly04)
        Dim lblDollyInfo04 As New System.Windows.Forms.Label()
        lblDollyInfo04.Text = "(1.00 = Vừa vặn khung hình)"
        lblDollyInfo04.Location = New System.Drawing.Point(322, 22) : lblDollyInfo04.Size = New System.Drawing.Size(180, 20)
        lblDollyInfo04.Font = New System.Drawing.Font("Segoe UI", 8.0!, FontStyle.Italic)
        lblDollyInfo04.ForeColor = System.Drawing.Color.FromArgb(20, 120, 60)
        grpZoom04.Controls.Add(lblDollyInfo04)

        Dim lblNormFOV04 As New System.Windows.Forms.Label()
        lblNormFOV04.Text = "Góc mở ống kính thường (FOV):"
        lblNormFOV04.Location = New System.Drawing.Point(14, 52) : lblNormFOV04.Size = New System.Drawing.Size(200, 20)
        grpZoom04.Controls.Add(lblNormFOV04)
        Dim numNormFOV04 As New System.Windows.Forms.NumericUpDown()
        numNormFOV04.Location = New System.Drawing.Point(220, 50) : numNormFOV04.Size = New System.Drawing.Size(95, 22)
        numNormFOV04.DecimalPlaces = 1 : numNormFOV04.Increment = 1.0D : numNormFOV04.Minimum = 5.0D : numNormFOV04.Maximum = 150.0D
        numNormFOV04.Value = CDec(s04.NormalFOV)
        grpZoom04.Controls.Add(numNormFOV04)
        Dim lblNormFOVInfo04 As New System.Windows.Forms.Label()
        lblNormFOVInfo04.Text = "(52° = Góc nhìn tự nhiên)"
        lblNormFOVInfo04.Location = New System.Drawing.Point(322, 52) : lblNormFOVInfo04.Size = New System.Drawing.Size(180, 20)
        lblNormFOVInfo04.Font = New System.Drawing.Font("Segoe UI", 8.0!, FontStyle.Italic)
        lblNormFOVInfo04.ForeColor = System.Drawing.Color.FromArgb(20, 120, 60)
        grpZoom04.Controls.Add(lblNormFOVInfo04)

        Dim lblZoomFOV04 As New System.Windows.Forms.Label()
        lblZoomFOV04.Text = "Góc mở khi Zoom Macro (FOV):"
        lblZoomFOV04.Location = New System.Drawing.Point(14, 82) : lblZoomFOV04.Size = New System.Drawing.Size(200, 20)
        grpZoom04.Controls.Add(lblZoomFOV04)
        Dim numZoomFOV04 As New System.Windows.Forms.NumericUpDown()
        numZoomFOV04.Location = New System.Drawing.Point(220, 80) : numZoomFOV04.Size = New System.Drawing.Size(95, 22)
        numZoomFOV04.DecimalPlaces = 1 : numZoomFOV04.Increment = 1.0D : numZoomFOV04.Minimum = 2.0D : numZoomFOV04.Maximum = 150.0D
        numZoomFOV04.Value = CDec(s04.ZoomFOV)
        grpZoom04.Controls.Add(numZoomFOV04)
        Dim lblZoomFOVInfo04 As New System.Windows.Forms.Label()
        lblZoomFOVInfo04.Text = "(32° = Macro Telephoto sắc sảo)"
        lblZoomFOVInfo04.Location = New System.Drawing.Point(322, 82) : lblZoomFOVInfo04.Size = New System.Drawing.Size(180, 20)
        lblZoomFOVInfo04.Font = New System.Drawing.Font("Segoe UI", 8.0!, FontStyle.Italic)
        lblZoomFOVInfo04.ForeColor = System.Drawing.Color.FromArgb(20, 120, 60)
        grpZoom04.Controls.Add(lblZoomFOVInfo04)

        Dim lblOrbitR04 As New System.Windows.Forms.Label()
        lblOrbitR04.Text = "Cự ly đa giác ngoài (Orbit):"
        lblOrbitR04.Location = New System.Drawing.Point(14, 112) : lblOrbitR04.Size = New System.Drawing.Size(200, 20)
        grpZoom04.Controls.Add(lblOrbitR04)
        Dim numOrbitR04 As New System.Windows.Forms.NumericUpDown()
        numOrbitR04.Location = New System.Drawing.Point(220, 110) : numOrbitR04.Size = New System.Drawing.Size(95, 22)
        numOrbitR04.DecimalPlaces = 2 : numOrbitR04.Increment = 0.1D : numOrbitR04.Minimum = 0.05D : numOrbitR04.Maximum = 50.0D
        numOrbitR04.Value = CDec(s04.OrbitDistanceScale)
        grpZoom04.Controls.Add(numOrbitR04)
        Dim lblOrbitRInfo04 As New System.Windows.Forms.Label()
        lblOrbitRInfo04.Text = "(3.00 = Bao quát từ xa)"
        lblOrbitRInfo04.Location = New System.Drawing.Point(322, 112) : lblOrbitRInfo04.Size = New System.Drawing.Size(180, 20)
        lblOrbitRInfo04.Font = New System.Drawing.Font("Segoe UI", 8.0!, FontStyle.Italic)
        lblOrbitRInfo04.ForeColor = System.Drawing.Color.FromArgb(20, 120, 60)
        grpZoom04.Controls.Add(lblOrbitRInfo04)

        ' Bento 3: Nhịp Điệu Dừng Ngắm & Gia Tốc (Micro-Hold & Dynamics)
        Dim grpHold04 As New System.Windows.Forms.GroupBox()
        grpHold04.Text = " 3. NHỊP ĐIỆU DỪNG NGẮM && ĐỘ NGHIÊNG CÁNH (MICRO-HOLD) "
        grpHold04.Location = New System.Drawing.Point(12, 360) : grpHold04.Size = New System.Drawing.Size(516, 115)
        grpHold04.BackColor = System.Drawing.Color.White
        page04.Controls.Add(grpHold04)

        Dim lblHoldSec04 As New System.Windows.Forms.Label()
        lblHoldSec04.Text = "Thời gian ngắm tại mỗi điểm (giây):"
        lblHoldSec04.Location = New System.Drawing.Point(14, 25) : lblHoldSec04.Size = New System.Drawing.Size(200, 20)
        grpHold04.Controls.Add(lblHoldSec04)
        Dim numHoldSec04 As New System.Windows.Forms.NumericUpDown()
        numHoldSec04.Location = New System.Drawing.Point(220, 23) : numHoldSec04.Size = New System.Drawing.Size(95, 22)
        numHoldSec04.DecimalPlaces = 2 : numHoldSec04.Increment = 0.05D : numHoldSec04.Minimum = 0.0D : numHoldSec04.Maximum = 60.0D
        numHoldSec04.Value = CDec(s04.MicroHoldSeconds)
        grpHold04.Controls.Add(numHoldSec04)
        Dim lblHoldInfo04 As New System.Windows.Forms.Label()
        lblHoldInfo04.Text = "(0.30s = Nhịp ghìm phanh đĩnh đạc)"
        lblHoldInfo04.Location = New System.Drawing.Point(322, 25) : lblHoldInfo04.Size = New System.Drawing.Size(180, 20)
        lblHoldInfo04.Font = New System.Drawing.Font("Segoe UI", 8.0!, FontStyle.Italic)
        lblHoldInfo04.ForeColor = System.Drawing.Color.FromArgb(20, 120, 60)
        grpHold04.Controls.Add(lblHoldInfo04)

        Dim lblBank04 As New System.Windows.Forms.Label()
        lblBank04.Text = "Độ nghiêng cánh khi lướt (độ):"
        lblBank04.Location = New System.Drawing.Point(14, 55) : lblBank04.Size = New System.Drawing.Size(200, 20)
        grpHold04.Controls.Add(lblBank04)
        Dim numBank04 As New System.Windows.Forms.NumericUpDown()
        numBank04.Location = New System.Drawing.Point(220, 53) : numBank04.Size = New System.Drawing.Size(95, 22)
        numBank04.DecimalPlaces = 1 : numBank04.Increment = 1.0D : numBank04.Minimum = -89.0D : numBank04.Maximum = 89.0D
        numBank04.Value = CDec(s04.BankApex)
        grpHold04.Controls.Add(numBank04)

        Dim lblElev04 As New System.Windows.Forms.Label()
        lblElev04.Text = "Cao độ góc nhìn 3/4 trên (độ):"
        lblElev04.Location = New System.Drawing.Point(14, 85) : lblElev04.Size = New System.Drawing.Size(200, 20)
        grpHold04.Controls.Add(lblElev04)
        Dim numElev04 As New System.Windows.Forms.NumericUpDown()
        numElev04.Location = New System.Drawing.Point(220, 83) : numElev04.Size = New System.Drawing.Size(95, 22)
        numElev04.DecimalPlaces = 1 : numElev04.Increment = 1.0D : numElev04.Minimum = -89.0D : numElev04.Maximum = 89.0D
        numElev04.Value = CDec(s04.ElevationDeg)
        grpHold04.Controls.Add(numElev04)

        ' Bento 4: Thông số Chuyển động & Gia tốc Cảnh 4
        Dim grpParams04 As New System.Windows.Forms.GroupBox()
        grpParams04.Text = " 4. THÔNG SỐ CHUYỂN ĐỘNG && GIA TỐC CẢNH 4 "
        grpParams04.Location = New System.Drawing.Point(12, 482) : grpParams04.Size = New System.Drawing.Size(516, 115)
        grpParams04.BackColor = System.Drawing.Color.White
        page04.Controls.Add(grpParams04)

        Dim lblDur04 As New System.Windows.Forms.Label()
        lblDur04.Text = "Thời lượng tổng chuyển động (giây):"
        lblDur04.Location = New System.Drawing.Point(16, 22) : lblDur04.Size = New System.Drawing.Size(240, 18)
        grpParams04.Controls.Add(lblDur04)
        Dim numDur04 As New System.Windows.Forms.NumericUpDown()
        numDur04.Location = New System.Drawing.Point(280, 20) : numDur04.Size = New System.Drawing.Size(120, 22)
        numDur04.DecimalPlaces = 1 : numDur04.Increment = 0.5D : numDur04.Minimum = 0.1D : numDur04.Maximum = 300.0D
        numDur04.Value = CDec(s04.DurationSeconds)
        grpParams04.Controls.Add(numDur04)

        Dim lblSpeed04 As New System.Windows.Forms.Label()
        lblSpeed04.Text = "Tốc độ bay (Hệ số Speed):"
        lblSpeed04.Location = New System.Drawing.Point(16, 50) : lblSpeed04.Size = New System.Drawing.Size(240, 18)
        grpParams04.Controls.Add(lblSpeed04)
        Dim numSpeed04 As New System.Windows.Forms.NumericUpDown()
        numSpeed04.Location = New System.Drawing.Point(280, 48) : numSpeed04.Size = New System.Drawing.Size(120, 22)
        numSpeed04.DecimalPlaces = 2 : numSpeed04.Increment = 0.1D : numSpeed04.Minimum = 0.01D : numSpeed04.Maximum = 50.0D
        numSpeed04.Value = CDec(s04.SpeedMultiplier)
        grpParams04.Controls.Add(numSpeed04)

        Dim lblSpeedInfo04 As New System.Windows.Forms.Label()
        lblSpeedInfo04.Location = New System.Drawing.Point(16, 76) : lblSpeedInfo04.Size = New System.Drawing.Size(480, 25)
        lblSpeedInfo04.Font = New System.Drawing.Font("Segoe UI", 8.25!, FontStyle.Italic)
        lblSpeedInfo04.ForeColor = System.Drawing.Color.FromArgb(20, 120, 60)
        grpParams04.Controls.Add(lblSpeedInfo04)

        Dim updateSpeedLabel04 As Action = Sub()
            Dim dur As Double = CDbl(numDur04.Value)
            Dim spd As Double = CDbl(numSpeed04.Value)
            Dim realDur As Double = dur / Math.Max(0.05, spd)
            Dim nPts As Integer = If(cboMode04.SelectedIndex = 1, 3, (If(cboMode04.SelectedIndex = 2, Math.Max(2, s04.CustomPickPoints.Count), 4)))
            Dim perPt As Double = realDur / CDbl(nPts)
            lblSpeedInfo04.Text = "Thời gian chạy Cảnh 4: " & realDur.ToString("F1") & "s (" & spd.ToString("F2") & "x) | " & nPts.ToString() & " điểm soi (~" & perPt.ToString("F1") & "s/điểm)"
        End Sub

        AddHandler numDur04.ValueChanged, Sub(s As Object, e As EventArgs) updateSpeedLabel04()
        AddHandler numSpeed04.ValueChanged, Sub(s As Object, e As EventArgs) updateSpeedLabel04()
        AddHandler cboMode04.SelectedIndexChanged, Sub(s As Object, e As EventArgs) updateSpeedLabel04()
        updateSpeedLabel04()

        Dim applySettings04 As Action = Sub()
            Select Case cboMode04.SelectedIndex
                Case 1 : s04.PointsMode = "3_POINTS"
                Case 2 : s04.PointsMode = "CUSTOM_PICK"
                Case Else : s04.PointsMode = "4_POINTS"
            End Select

            Select Case cboApproach04.SelectedIndex
                Case 1 : s04.ApproachMode = "RECORDED_VIEW"
                Case 2 : s04.ApproachMode = "ISOMETRIC_FL"
                Case 3 : s04.ApproachMode = "ISOMETRIC_FR"
                Case 4 : s04.ApproachMode = "FRONT_LOOK"
                Case 5 : s04.ApproachMode = "TOP_DOWN"
                Case Else : s04.ApproachMode = "AUTO_EXTERIOR"
            End Select

            s04.ZoomDollyScale = CDbl(numDolly04.Value)
            s04.NormalFOV = CDbl(numNormFOV04.Value)
            s04.ZoomFOV = CDbl(numZoomFOV04.Value)
            s04.OrbitDistanceScale = CDbl(numOrbitR04.Value)

            s04.MicroHoldSeconds = CDbl(numHoldSec04.Value)
            s04.BankApex = CDbl(numBank04.Value)
            s04.ElevationDeg = CDbl(numElev04.Value)

            s04.DurationSeconds = CDbl(numDur04.Value)
            s04.SpeedMultiplier = CDbl(numSpeed04.Value)
        End Sub

        ' ======================================================================
        ' TAB 5: CẢNH 5 — TWIN WHIP ARCS -> HERO HOLD -> GRAND ESCAPE REVEAL
        ' ======================================================================

        Dim page05 As New System.Windows.Forms.TabPage()
        page05.Text = "🎬 CẢNH 5: ESCAPE REVEAL"
        page05.BackColor = System.Drawing.Color.FromArgb(248, 249, 250)
        page05.AutoScroll = True
        tabStudio.TabPages.Add(page05)

        ' Bento 1: Tiêu điểm Hero & Góc 3/4 Xuất Phát Quay
        Dim grpHero05 As New System.Windows.Forms.GroupBox()
        grpHero05.Text = " 1. TIÊU ĐIỂM HERO && GÓC 3/4 XUẤT PHÁT QUAY "
        grpHero05.Location = New System.Drawing.Point(12, 10) : grpHero05.Size = New System.Drawing.Size(516, 175)
        grpHero05.BackColor = System.Drawing.Color.White
        page05.Controls.Add(grpHero05)

        Dim lblHero05 As New System.Windows.Forms.Label()
        lblHero05.Text = "Linh kiện tâm điểm kết phim:"
        lblHero05.Location = New System.Drawing.Point(14, 22) : lblHero05.Size = New System.Drawing.Size(180, 20)
        grpHero05.Controls.Add(lblHero05)

        Dim cboHero05 As New System.Windows.Forms.ComboBox()
        cboHero05.DropDownStyle = ComboBoxStyle.DropDownList
        cboHero05.Location = New System.Drawing.Point(200, 19) : cboHero05.Size = New System.Drawing.Size(300, 24)
        cboHero05.Font = New System.Drawing.Font("Segoe UI", 8.5!, FontStyle.Bold)
        cboHero05.ForeColor = System.Drawing.Color.FromArgb(20, 100, 50)
        cboHero05.Items.Add("Cụm Bơm Cao Áp & Đầu Hút [Khuyến nghị]")
        cboHero05.Items.Add("Cụm Màng Lọc RO/UF & Van")
        cboHero05.Items.Add("Tủ Điện Điều Khiển PLC & Đèn Báo")
        cboHero05.Items.Add("Tâm Toàn Bộ Skid")
        cboHero05.Items.Add("📌 Điểm cuối cùng chọn ở Cảnh 4 (Last Pick)")
        cboHero05.SelectedIndex = 3
        grpHero05.Controls.Add(cboHero05)

        ' Chọn Góc 3/4 bắt đầu quay
        Dim lblCorner05 As New System.Windows.Forms.Label()
        lblCorner05.Text = "Góc 3/4 xuất phát quay:"
        lblCorner05.Location = New System.Drawing.Point(14, 52) : lblCorner05.Size = New System.Drawing.Size(180, 20)
        grpHero05.Controls.Add(lblCorner05)

        Dim cboStartCorner05 As New System.Windows.Forms.ComboBox()
        cboStartCorner05.DropDownStyle = ComboBoxStyle.DropDownList
        cboStartCorner05.Location = New System.Drawing.Point(200, 49) : cboStartCorner05.Size = New System.Drawing.Size(300, 24)
        cboStartCorner05.Font = New System.Drawing.Font("Segoe UI", 8.5!, FontStyle.Bold)
        cboStartCorner05.ForeColor = System.Drawing.Color.FromArgb(20, 100, 50)
        cboStartCorner05.Items.Add("Góc 1: Trước - Trái (-X, -Z) [Mặc định]")
        cboStartCorner05.Items.Add("Góc 2: Trước - Phải (+X, -Z)")
        cboStartCorner05.Items.Add("Góc 3: Sau - Phải (+X, +Z)")
        cboStartCorner05.Items.Add("Góc 4: Sau - Trái (-X, +Z)")
        cboStartCorner05.Items.Add("Theo góc nhìn màn hình 3D hiện tại (Current View)")
        cboStartCorner05.Items.Add("Nối tiếp mượt từ điểm kết thúc Cảnh 4 (Seamless)")
        cboStartCorner05.SelectedIndex = 0
        grpHero05.Controls.Add(cboStartCorner05)

        ' RadioButtons Cao độ góc nhìn 3/4
        Dim radTop05 As New System.Windows.Forms.RadioButton()
        radTop05.Text = "▲ 3/4 TRÊN"
        radTop05.Checked = True
        radTop05.Location = New System.Drawing.Point(14, 80) : radTop05.Size = New System.Drawing.Size(110, 22)
        radTop05.Font = New System.Drawing.Font("Segoe UI", 8.5!, FontStyle.Bold)
        radTop05.ForeColor = System.Drawing.Color.FromArgb(20, 100, 50)
        grpHero05.Controls.Add(radTop05)

        Dim radLevel05 As New System.Windows.Forms.RadioButton()
        radLevel05.Text = "■ 3/4 NGANG"
        radLevel05.Location = New System.Drawing.Point(135, 80) : radLevel05.Size = New System.Drawing.Size(120, 22)
        radLevel05.Font = New System.Drawing.Font("Segoe UI", 8.5!, FontStyle.Bold)
        grpHero05.Controls.Add(radLevel05)

        Dim radBottom05 As New System.Windows.Forms.RadioButton()
        radBottom05.Text = "▼ 3/4 DƯỚI"
        radBottom05.Location = New System.Drawing.Point(265, 80) : radBottom05.Size = New System.Drawing.Size(110, 22)
        radBottom05.Font = New System.Drawing.Font("Segoe UI", 8.5!, FontStyle.Bold)
        grpHero05.Controls.Add(radBottom05)

        ' Ô số Cao độ (Elevation) & Bán kính (Orbit Radius)
        Dim lblElev05 As New System.Windows.Forms.Label()
        lblElev05.Text = "Cao độ góc nhìn (độ):"
        lblElev05.Location = New System.Drawing.Point(14, 110) : lblElev05.Size = New System.Drawing.Size(140, 20)
        grpHero05.Controls.Add(lblElev05)
        Dim numElev05 As New System.Windows.Forms.NumericUpDown()
        numElev05.Location = New System.Drawing.Point(155, 108) : numElev05.Size = New System.Drawing.Size(85, 22)
        numElev05.DecimalPlaces = 1 : numElev05.Increment = 5.0D : numElev05.Minimum = -89.0D : numElev05.Maximum = 89.0D
        numElev05.Value = CDec(s05.ElevationDeg)
        grpHero05.Controls.Add(numElev05)

        Dim lblOrbitR05 As New System.Windows.Forms.Label()
        lblOrbitR05.Text = "Bán kính xoay (Radius):"
        lblOrbitR05.Location = New System.Drawing.Point(255, 110) : lblOrbitR05.Size = New System.Drawing.Size(145, 20)
        grpHero05.Controls.Add(lblOrbitR05)
        Dim numOrbitR05 As New System.Windows.Forms.NumericUpDown()
        numOrbitR05.Location = New System.Drawing.Point(405, 108) : numOrbitR05.Size = New System.Drawing.Size(95, 22)
        numOrbitR05.DecimalPlaces = 2 : numOrbitR05.Increment = 0.2D : numOrbitR05.Minimum = 0.1D : numOrbitR05.Maximum = 30.0D
        numOrbitR05.Value = CDec(s05.OrbitRadiusScale)
        grpHero05.Controls.Add(numOrbitR05)

        Dim lblElevInfo05 As New System.Windows.Forms.Label()
        lblElevInfo05.Text = "✔ Góc nhìn 3/4 Trên (+25°), bao quát đầu nắp màng, bơm, van và đường ống"
        lblElevInfo05.Location = New System.Drawing.Point(14, 140) : lblElevInfo05.Size = New System.Drawing.Size(485, 25)
        lblElevInfo05.Font = New System.Drawing.Font("Segoe UI", 8.0!, FontStyle.Italic)
        lblElevInfo05.ForeColor = System.Drawing.Color.FromArgb(20, 120, 60)
        grpHero05.Controls.Add(lblElevInfo05)

        AddHandler radTop05.CheckedChanged, Sub(s As Object, e As EventArgs)
            If radTop05.Checked Then
                numElev05.Value = 25.0D
                lblElevInfo05.Text = "✔ Góc nhìn 3/4 Trên (+25°), bao quát đầu nắp màng, bơm, van và đường ống"
            End If
        End Sub
        AddHandler radLevel05.CheckedChanged, Sub(s As Object, e As EventArgs)
            If radLevel05.Checked Then
                numElev05.Value = 0.0D
                lblElevInfo05.Text = "✔ Góc nhìn 3/4 Ngang (0°), ngang bằng tầm mắt kỹ thuật chuẩn xác"
            End If
        End Sub
        AddHandler radBottom05.CheckedChanged, Sub(s As Object, e As EventArgs)
            If radBottom05.Checked Then
                numElev05.Value = -10.0D
                lblElevInfo05.Text = "✔ Góc nhìn 3/4 Dưới (-10°), hất từ chân bệ máy lên bề thế, uy lực"
            End If
        End Sub

        ' Bento 2: Thông số Cú Búng Tốc & Quỹ Đạo Xoay Bay Quanh
        Dim grpWhip05 As New System.Windows.Forms.GroupBox()
        grpWhip05.Text = " 2. QUỸ ĐẠO BAY XOAY QUANH MÔ HÌNH (HELICAL ORBIT FLY-AROUND) "
        grpWhip05.Location = New System.Drawing.Point(12, 195) : grpWhip05.Size = New System.Drawing.Size(516, 205)
        grpWhip05.BackColor = System.Drawing.Color.White
        page05.Controls.Add(grpWhip05)

        Dim lblSweep05 As New System.Windows.Forms.Label()
        lblSweep05.Text = "Cung quét xoay quanh máy:"
        lblSweep05.Location = New System.Drawing.Point(14, 25) : lblSweep05.Size = New System.Drawing.Size(200, 20)
        grpWhip05.Controls.Add(lblSweep05)
        Dim cboSweep05 As New System.Windows.Forms.ComboBox()
        cboSweep05.DropDownStyle = ComboBoxStyle.DropDownList
        cboSweep05.Location = New System.Drawing.Point(220, 22) : cboSweep05.Size = New System.Drawing.Size(280, 24)
        cboSweep05.Font = New System.Drawing.Font("Segoe UI", 8.25!, FontStyle.Bold)
        cboSweep05.ForeColor = System.Drawing.Color.FromArgb(20, 100, 50)
        cboSweep05.Items.Add("Xoay Nửa Vòng (180° Orbit Sweep) [Khuyên dùng]")
        cboSweep05.Items.Add("Xoay 3/4 Vòng (270° Orbit Sweep)")
        cboSweep05.Items.Add("Xoay Trọn 1 Vòng (360° Full Helical Orbit)")
        cboSweep05.Items.Add("Xoay 2 Vòng (720° Double Helical Orbit)")
        cboSweep05.Items.Add("Tự nhập góc quét tùy ý (Nhập ô bên dưới)")
        cboSweep05.SelectedIndex = 3
        grpWhip05.Controls.Add(cboSweep05)

        ' Ô nhập góc quét xoay tùy ý
        Dim lblCustomSweep05 As New System.Windows.Forms.Label()
        lblCustomSweep05.Text = "Góc quét xoay tùy chỉnh (độ):"
        lblCustomSweep05.Location = New System.Drawing.Point(14, 55) : lblCustomSweep05.Size = New System.Drawing.Size(200, 20)
        grpWhip05.Controls.Add(lblCustomSweep05)
        Dim numSweepDeg05 As New System.Windows.Forms.NumericUpDown()
        numSweepDeg05.Location = New System.Drawing.Point(220, 52) : numSweepDeg05.Size = New System.Drawing.Size(95, 22)
        numSweepDeg05.DecimalPlaces = 1 : numSweepDeg05.Increment = 15.0D : numSweepDeg05.Minimum = 10.0D : numSweepDeg05.Maximum = 1440.0D
        numSweepDeg05.Value = CDec(s05.OrbitSweepDeg)
        grpWhip05.Controls.Add(numSweepDeg05)
        Dim lblSweepDegInfo05 As New System.Windows.Forms.Label()
        lblSweepDegInfo05.Text = "(180°=nửa vòng, 360°=1 vòng, 720°=2 vòng)"
        lblSweepDegInfo05.Location = New System.Drawing.Point(322, 54) : lblSweepDegInfo05.Size = New System.Drawing.Size(185, 20)
        lblSweepDegInfo05.Font = New System.Drawing.Font("Segoe UI", 7.75!, FontStyle.Italic)
        lblSweepDegInfo05.ForeColor = System.Drawing.Color.FromArgb(20, 120, 60)
        grpWhip05.Controls.Add(lblSweepDegInfo05)

        AddHandler cboSweep05.SelectedIndexChanged, Sub(s As Object, e As EventArgs)
            Select Case cboSweep05.SelectedIndex
                Case 0 : numSweepDeg05.Value = 180.0D
                Case 1 : numSweepDeg05.Value = 270.0D
                Case 2 : numSweepDeg05.Value = 360.0D
                Case 3 : numSweepDeg05.Value = 720.0D
            End Select
        End Sub

        AddHandler numSweepDeg05.ValueChanged, Sub(s As Object, e As EventArgs)
            Dim val As Double = CDbl(numSweepDeg05.Value)
            If Math.Abs(val - 180.0) < 0.1 Then
                If cboSweep05.SelectedIndex <> 0 Then cboSweep05.SelectedIndex = 0
            ElseIf Math.Abs(val - 270.0) < 0.1 Then
                If cboSweep05.SelectedIndex <> 1 Then cboSweep05.SelectedIndex = 1
            ElseIf Math.Abs(val - 360.0) < 0.1 Then
                If cboSweep05.SelectedIndex <> 2 Then cboSweep05.SelectedIndex = 2
            ElseIf Math.Abs(val - 720.0) < 0.1 Then
                If cboSweep05.SelectedIndex <> 3 Then cboSweep05.SelectedIndex = 3
            Else
                If cboSweep05.SelectedIndex <> 4 Then cboSweep05.SelectedIndex = 4
            End If
        End Sub

        Dim lblDir05 As New System.Windows.Forms.Label()
        lblDir05.Text = "Chiều bay xoay quanh máy:"
        lblDir05.Location = New System.Drawing.Point(14, 85) : lblDir05.Size = New System.Drawing.Size(200, 20)
        grpWhip05.Controls.Add(lblDir05)
        Dim cboDir05 As New System.Windows.Forms.ComboBox()
        cboDir05.DropDownStyle = ComboBoxStyle.DropDownList
        cboDir05.Location = New System.Drawing.Point(220, 82) : cboDir05.Size = New System.Drawing.Size(280, 24)
        cboDir05.Font = New System.Drawing.Font("Segoe UI", 8.25!, FontStyle.Bold)
        cboDir05.ForeColor = System.Drawing.Color.FromArgb(20, 100, 50)
        cboDir05.Items.Add("Ngược Chiều Kim Đồng Hồ (Trước ➔ Hông Phải ➔ Sau)")
        cboDir05.Items.Add("Thuận Chiều Kim Đồng Hồ (Trước ➔ Hông Trái ➔ Sau)")
        cboDir05.SelectedIndex = 0
        grpWhip05.Controls.Add(cboDir05)

        Dim lblBank05 As New System.Windows.Forms.Label()
        lblBank05.Text = "Độ lật nghiêng cánh khi lướt (độ):"
        lblBank05.Location = New System.Drawing.Point(14, 115) : lblBank05.Size = New System.Drawing.Size(200, 20)
        grpWhip05.Controls.Add(lblBank05)
        Dim numBank05 As New System.Windows.Forms.NumericUpDown()
        numBank05.Location = New System.Drawing.Point(220, 113) : numBank05.Size = New System.Drawing.Size(95, 22)
        numBank05.DecimalPlaces = 1 : numBank05.Increment = 1.0D : numBank05.Minimum = -89.0D : numBank05.Maximum = 89.0D
        numBank05.Value = CDec(s05.BankWhipDeg)
        grpWhip05.Controls.Add(numBank05)
        Dim lblBankInfo05 As New System.Windows.Forms.Label()
        lblBankInfo05.Text = "(12° = Ôm cua Dutch Roll FPV)"
        lblBankInfo05.Location = New System.Drawing.Point(322, 115) : lblBankInfo05.Size = New System.Drawing.Size(180, 20)
        lblBankInfo05.Font = New System.Drawing.Font("Segoe UI", 8.0!, FontStyle.Italic)
        lblBankInfo05.ForeColor = System.Drawing.Color.FromArgb(20, 120, 60)
        grpWhip05.Controls.Add(lblBankInfo05)

        Dim lblPass05 As New System.Windows.Forms.Label()
        lblPass05.Text = "Cự ly lướt sát mạn sườn (Pass):"
        lblPass05.Location = New System.Drawing.Point(14, 145) : lblPass05.Size = New System.Drawing.Size(200, 20)
        grpWhip05.Controls.Add(lblPass05)
        Dim numPass05 As New System.Windows.Forms.NumericUpDown()
        numPass05.Location = New System.Drawing.Point(220, 143) : numPass05.Size = New System.Drawing.Size(95, 22)
        numPass05.DecimalPlaces = 2 : numPass05.Increment = 0.05D : numPass05.Minimum = 0.01D : numPass05.Maximum = 20.0D
        numPass05.Value = CDec(s05.ClosePassScale)
        grpWhip05.Controls.Add(numPass05)
        Dim lblPassInfo05 As New System.Windows.Forms.Label()
        lblPassInfo05.Text = "(0.45x = Parallax tiền cảnh xé gió)"
        lblPassInfo05.Location = New System.Drawing.Point(322, 145) : lblPassInfo05.Size = New System.Drawing.Size(180, 20)
        lblPassInfo05.Font = New System.Drawing.Font("Segoe UI", 8.0!, FontStyle.Italic)
        lblPassInfo05.ForeColor = System.Drawing.Color.FromArgb(20, 120, 60)
        grpWhip05.Controls.Add(lblPassInfo05)

        Dim lblHold05 As New System.Windows.Forms.Label()
        lblHold05.Text = "Thời gian phanh cứng ngắm Hero:"
        lblHold05.Location = New System.Drawing.Point(14, 175) : lblHold05.Size = New System.Drawing.Size(200, 20)
        grpWhip05.Controls.Add(lblHold05)
        Dim numHold05 As New System.Windows.Forms.NumericUpDown()
        numHold05.Location = New System.Drawing.Point(220, 173) : numHold05.Size = New System.Drawing.Size(95, 22)
        numHold05.DecimalPlaces = 2 : numHold05.Increment = 0.05D : numHold05.Minimum = 0.0D : numHold05.Maximum = 60.0D
        numHold05.Value = CDec(s05.HeroHoldSec)
        grpWhip05.Controls.Add(numHold05)
        Dim lblHoldInfo05 As New System.Windows.Forms.Label()
        lblHoldInfo05.Text = "(0.50s = Đóng băng ngắm sắc sảo)"
        lblHoldInfo05.Location = New System.Drawing.Point(322, 175) : lblHoldInfo05.Size = New System.Drawing.Size(180, 20)
        lblHoldInfo05.Font = New System.Drawing.Font("Segoe UI", 8.0!, FontStyle.Italic)
        lblHoldInfo05.ForeColor = System.Drawing.Color.FromArgb(20, 120, 60)
        grpWhip05.Controls.Add(lblHoldInfo05)

        ' Bento 3: Cấu hình Grand Escape Thoát Ly Kết Phim
        Dim grpEscape05 As New System.Windows.Forms.GroupBox()
        grpEscape05.Text = " 3. THÔNG SỐ GRAND ESCAPE THOÁT LY (OUTRO REVEAL) "
        grpEscape05.Location = New System.Drawing.Point(12, 410) : grpEscape05.Size = New System.Drawing.Size(516, 115)
        grpEscape05.BackColor = System.Drawing.Color.White
        page05.Controls.Add(grpEscape05)

        Dim lblEscDist05 As New System.Windows.Forms.Label()
        lblEscDist05.Text = "Cự ly bung lùi xa thoát ly:"
        lblEscDist05.Location = New System.Drawing.Point(14, 25) : lblEscDist05.Size = New System.Drawing.Size(200, 20)
        grpEscape05.Controls.Add(lblEscDist05)
        Dim numEscDist05 As New System.Windows.Forms.NumericUpDown()
        numEscDist05.Location = New System.Drawing.Point(220, 23) : numEscDist05.Size = New System.Drawing.Size(95, 22)
        numEscDist05.DecimalPlaces = 1 : numEscDist05.Increment = 0.5D : numEscDist05.Minimum = 0.1D : numEscDist05.Maximum = 100.0D
        numEscDist05.Value = CDec(s05.EscapeDistanceScale)
        grpEscape05.Controls.Add(numEscDist05)
        Dim lblEscDistInfo05 As New System.Windows.Forms.Label()
        lblEscDistInfo05.Text = "(3.5x = Rút xa bao quát hoành tráng)"
        lblEscDistInfo05.Location = New System.Drawing.Point(322, 25) : lblEscDistInfo05.Size = New System.Drawing.Size(180, 20)
        lblEscDistInfo05.Font = New System.Drawing.Font("Segoe UI", 8.0!, FontStyle.Italic)
        lblEscDistInfo05.ForeColor = System.Drawing.Color.FromArgb(20, 120, 60)
        grpEscape05.Controls.Add(lblEscDistInfo05)

        Dim lblClimb05 As New System.Windows.Forms.Label()
        lblClimb05.Text = "Cao độ bốc đầu nâng góc máy:"
        lblClimb05.Location = New System.Drawing.Point(14, 55) : lblClimb05.Size = New System.Drawing.Size(200, 20)
        grpEscape05.Controls.Add(lblClimb05)
        Dim numClimb05 As New System.Windows.Forms.NumericUpDown()
        numClimb05.Location = New System.Drawing.Point(220, 53) : numClimb05.Size = New System.Drawing.Size(95, 22)
        numClimb05.DecimalPlaces = 1 : numClimb05.Increment = 0.2D : numClimb05.Minimum = -20.0D : numClimb05.Maximum = 50.0D
        numClimb05.Value = CDec(s05.EscapeClimbScale)
        grpEscape05.Controls.Add(numClimb05)
        Dim lblClimbInfo05 As New System.Windows.Forms.Label()
        lblClimbInfo05.Text = "(1.6x = Bốc cao góc nhìn uy lực)"
        lblClimbInfo05.Location = New System.Drawing.Point(322, 55) : lblClimbInfo05.Size = New System.Drawing.Size(180, 20)
        lblClimbInfo05.Font = New System.Drawing.Font("Segoe UI", 8.0!, FontStyle.Italic)
        lblClimbInfo05.ForeColor = System.Drawing.Color.FromArgb(20, 120, 60)
        grpEscape05.Controls.Add(lblClimbInfo05)

        Dim lblEscFOV05 As New System.Windows.Forms.Label()
        lblEscFOV05.Text = "Góc mở ống kính kết thúc (FOV):"
        lblEscFOV05.Location = New System.Drawing.Point(14, 85) : lblEscFOV05.Size = New System.Drawing.Size(200, 20)
        grpEscape05.Controls.Add(lblEscFOV05)
        Dim numEscFOV05 As New System.Windows.Forms.NumericUpDown()
        numEscFOV05.Location = New System.Drawing.Point(220, 83) : numEscFOV05.Size = New System.Drawing.Size(95, 22)
        numEscFOV05.DecimalPlaces = 1 : numEscFOV05.Increment = 1.0D : numEscFOV05.Minimum = 5.0D : numEscFOV05.Maximum = 160.0D
        numEscFOV05.Value = CDec(s05.EscapeFOV)
        grpEscape05.Controls.Add(numEscFOV05)
        Dim lblEscFOVInfo05 As New System.Windows.Forms.Label()
        lblEscFOVInfo05.Text = "(60° = Đại cảnh góc rộng)"
        lblEscFOVInfo05.Location = New System.Drawing.Point(322, 85) : lblEscFOVInfo05.Size = New System.Drawing.Size(180, 20)
        lblEscFOVInfo05.Font = New System.Drawing.Font("Segoe UI", 8.0!, FontStyle.Italic)
        lblEscFOVInfo05.ForeColor = System.Drawing.Color.FromArgb(20, 120, 60)
        grpEscape05.Controls.Add(lblEscFOVInfo05)

        ' Bento 4: Thông số Chuyển động Cảnh 5
        Dim grpParams05 As New System.Windows.Forms.GroupBox()
        grpParams05.Text = " 4. THÔNG SỐ CHUYỂN ĐỘNG && GIA TỐC CẢNH 5 "
        grpParams05.Location = New System.Drawing.Point(12, 535) : grpParams05.Size = New System.Drawing.Size(516, 115)
        grpParams05.BackColor = System.Drawing.Color.White
        page05.Controls.Add(grpParams05)

        Dim lblDur05 As New System.Windows.Forms.Label()
        lblDur05.Text = "Thời lượng tổng chuyển động (giây):"
        lblDur05.Location = New System.Drawing.Point(16, 22) : lblDur05.Size = New System.Drawing.Size(240, 18)
        grpParams05.Controls.Add(lblDur05)
        Dim numDur05 As New System.Windows.Forms.NumericUpDown()
        numDur05.Location = New System.Drawing.Point(280, 20) : numDur05.Size = New System.Drawing.Size(120, 22)
        numDur05.DecimalPlaces = 1 : numDur05.Increment = 0.5D : numDur05.Minimum = 0.1D : numDur05.Maximum = 300.0D
        numDur05.Value = CDec(s05.DurationSeconds)
        grpParams05.Controls.Add(numDur05)

        Dim lblSpeed05 As New System.Windows.Forms.Label()
        lblSpeed05.Text = "Tốc độ bay (Hệ số Speed):"
        lblSpeed05.Location = New System.Drawing.Point(16, 50) : lblSpeed05.Size = New System.Drawing.Size(240, 18)
        grpParams05.Controls.Add(lblSpeed05)
        Dim numSpeed05 As New System.Windows.Forms.NumericUpDown()
        numSpeed05.Location = New System.Drawing.Point(280, 48) : numSpeed05.Size = New System.Drawing.Size(120, 22)
        numSpeed05.DecimalPlaces = 2 : numSpeed05.Increment = 0.1D : numSpeed05.Minimum = 0.01D : numSpeed05.Maximum = 50.0D
        numSpeed05.Value = CDec(s05.SpeedMultiplier)
        grpParams05.Controls.Add(numSpeed05)

        Dim lblSpeedInfo05 As New System.Windows.Forms.Label()
        lblSpeedInfo05.Location = New System.Drawing.Point(16, 76) : lblSpeedInfo05.Size = New System.Drawing.Size(480, 25)
        lblSpeedInfo05.Font = New System.Drawing.Font("Segoe UI", 8.25!, FontStyle.Italic)
        lblSpeedInfo05.ForeColor = System.Drawing.Color.FromArgb(20, 120, 60)
        grpParams05.Controls.Add(lblSpeedInfo05)

        Dim updateSpeedLabel05 As Action = Sub()
            Dim dur As Double = CDbl(numDur05.Value)
            Dim spd As Double = CDbl(numSpeed05.Value)
            Dim realDur As Double = dur / Math.Max(0.05, spd)
            lblSpeedInfo05.Text = "Thời gian chạy Cảnh 5: " & realDur.ToString("F1") & "s (" & spd.ToString("F2") & "x) | 2 Cú Whip ➔ Hold ➔ Escape Reveal"
        End Sub

        AddHandler numDur05.ValueChanged, Sub(s As Object, e As EventArgs) updateSpeedLabel05()
        AddHandler numSpeed05.ValueChanged, Sub(s As Object, e As EventArgs) updateSpeedLabel05()
        updateSpeedLabel05()

        Dim applySettings05 As Action = Sub()
            Select Case cboHero05.SelectedIndex
                Case 1 : s05.FocusHeroKey = "MEMBRANE"
                Case 2 : s05.FocusHeroKey = "PANEL"
                Case 3 : s05.FocusHeroKey = "CENTER"
                Case 4 : s05.FocusHeroKey = "LAST_PICK"
                Case Else : s05.FocusHeroKey = "PUMP"
            End Select

            Select Case cboStartCorner05.SelectedIndex
                Case 1 : s05.StartCornerMode = "FRONT_RIGHT"
                Case 2 : s05.StartCornerMode = "BACK_RIGHT"
                Case 3 : s05.StartCornerMode = "BACK_LEFT"
                Case 4 : s05.StartCornerMode = "CURRENT_VIEW"
                Case 5 : s05.StartCornerMode = "PREV_SHOT"
                Case Else : s05.StartCornerMode = "FRONT_LEFT"
            End Select

            If radBottom05.Checked Then
                s05.ViewAngleMode = "34_BOTTOM"
            ElseIf radLevel05.Checked Then
                s05.ViewAngleMode = "34_LEVEL"
            Else
                s05.ViewAngleMode = "34_TOP"
            End If

            s05.ElevationDeg = CDbl(numElev05.Value)
            s05.OrbitRadiusScale = CDbl(numOrbitR05.Value)


            s05.OrbitSweepDeg = CDbl(numSweepDeg05.Value)

            s05.OrbitDirection = If(cboDir05.SelectedIndex = 1, "CW", "CCW")

            s05.BankWhipDeg = CDbl(numBank05.Value)
            s05.ClosePassScale = CDbl(numPass05.Value)
            s05.HeroHoldSec = CDbl(numHold05.Value)

            s05.EscapeDistanceScale = CDbl(numEscDist05.Value)
            s05.EscapeClimbScale = CDbl(numClimb05.Value)
            s05.EscapeFOV = CDbl(numEscFOV05.Value)

            s05.DurationSeconds = CDbl(numDur05.Value)
            s05.SpeedMultiplier = CDbl(numSpeed05.Value)
        End Sub

        ' ======================================================================
        ' TAB 6: GHÉP PHIM MASTER (FULL SHOWREEL)
        ' ======================================================================
        Dim pageMaster As New System.Windows.Forms.TabPage()
        pageMaster.Text = "🎞️ GHÉP PHIM MASTER"
        pageMaster.BackColor = System.Drawing.Color.FromArgb(248, 249, 250)
        pageMaster.AutoScroll = True
        tabStudio.TabPages.Add(pageMaster)

        Dim grpTimeline As New System.Windows.Forms.GroupBox()
        grpTimeline.Text = " 1. CÁC CẢNH THAM GIA GHÉP NỐI LIÊN HOÀN "
        grpTimeline.Location = New System.Drawing.Point(12, 10) : grpTimeline.Size = New System.Drawing.Size(516, 185)
        grpTimeline.BackColor = System.Drawing.Color.White
        pageMaster.Controls.Add(grpTimeline)

        Dim chkM01 As New System.Windows.Forms.CheckBox()
        chkM01.Text = "✔ Cảnh 1: Grand Fly-In & Fit View (Từ xa bay vào bao quát)"
        chkM01.Checked = True : chkM01.Location = New System.Drawing.Point(16, 23) : chkM01.Size = New System.Drawing.Size(470, 22)
        chkM01.Font = New System.Drawing.Font("Segoe UI", 9.0!, FontStyle.Bold)
        grpTimeline.Controls.Add(chkM01)

        Dim chkM02 As New System.Windows.Forms.CheckBox()
        chkM02.Text = "✔ Cảnh 2: Bay ra xa lại & Đổi góc 3/4 (Pull-Back & Orbit)"
        chkM02.Checked = True : chkM02.Location = New System.Drawing.Point(16, 53) : chkM02.Size = New System.Drawing.Size(470, 22)
        chkM02.Font = New System.Drawing.Font("Segoe UI", 9.0!, FontStyle.Bold)
        grpTimeline.Controls.Add(chkM02)

        Dim chkM03 As New System.Windows.Forms.CheckBox()
        chkM03.Text = "✔ Cảnh 3: Đong Đưa Con Lắc Mặt Tiền (Pendulum Sway)"
        chkM03.Checked = True : chkM03.Location = New System.Drawing.Point(16, 83) : chkM03.Size = New System.Drawing.Size(470, 22)
        chkM03.Font = New System.Drawing.Font("Segoe UI", 9.0!, FontStyle.Bold)
        grpTimeline.Controls.Add(chkM03)

        Dim chkM04 As New System.Windows.Forms.CheckBox()
        chkM04.Text = "✔ Cảnh 4: Macro Zoom Đa Điểm Soi Chi Tiết (Custom Picks)"
        chkM04.Checked = True : chkM04.Location = New System.Drawing.Point(16, 113) : chkM04.Size = New System.Drawing.Size(470, 22)
        chkM04.Font = New System.Drawing.Font("Segoe UI", 9.0!, FontStyle.Bold)
        grpTimeline.Controls.Add(chkM04)

        Dim chkM05 As New System.Windows.Forms.CheckBox()
        chkM05.Text = "✔ Cảnh 5: Helical Orbit Bay Vòng Quanh & Grand Escape"
        chkM05.Checked = True : chkM05.Location = New System.Drawing.Point(16, 143) : chkM05.Size = New System.Drawing.Size(470, 22)
        chkM05.Font = New System.Drawing.Font("Segoe UI", 9.0!, FontStyle.Bold)
        grpTimeline.Controls.Add(chkM05)

        Dim lblMasterDesc As New System.Windows.Forms.Label()
        lblMasterDesc.Text = "Chuỗi ghép nối liên hoàn: C1 (Bay vào) ➔ C2 (Lùi cong đổi góc 3/4) ➔ C3 (Con lắc mặt trước) ➔ C4 (Soi macro các điểm) ➔ C5 (Xoay vòng quanh & Bốc đầu thoát ly kết phim)."
        lblMasterDesc.Location = New System.Drawing.Point(14, 202) : lblMasterDesc.Size = New System.Drawing.Size(512, 34)
        lblMasterDesc.ForeColor = System.Drawing.Color.FromArgb(50, 60, 70)
        pageMaster.Controls.Add(lblMasterDesc)

        ' Bento Box 2: Cài đặt xuất Video TikTok / MP4
        Dim grpVideoSettings As New System.Windows.Forms.GroupBox()
        grpVideoSettings.Text = " 2. CÀI ĐẶT XUẤT VIDEO TIKTOK / CINEMATIC MP4 "
        grpVideoSettings.Location = New System.Drawing.Point(12, 242) : grpVideoSettings.Size = New System.Drawing.Size(516, 215)
        grpVideoSettings.BackColor = System.Drawing.Color.White
        pageMaster.Controls.Add(grpVideoSettings)

        Dim lblVFormat As New System.Windows.Forms.Label()
        lblVFormat.Text = "Định dạng Video:" : lblVFormat.Location = New System.Drawing.Point(16, 26) : lblVFormat.Size = New System.Drawing.Size(120, 20)
        grpVideoSettings.Controls.Add(lblVFormat)

        Dim cboVideoFormat As New System.Windows.Forms.ComboBox()
        cboVideoFormat.DropDownStyle = ComboBoxStyle.DropDownList
        cboVideoFormat.Items.Add("📱 TikTok 9:16 Full Dọc (1080x1920 RÕ NÉT 100% - KHÔNG MỜ NỀN) [Khuyên dùng]")
        cboVideoFormat.Items.Add("📱 TikTok 9:16 Mờ Trên & Dưới (Khung Ngang 16:9 + Nền Mờ Blur)")
        cboVideoFormat.Items.Add("🖥️ YouTube / Báo Cáo 16:9 (Full HD 1920x1080 Ngang)")
        cboVideoFormat.SelectedIndex = 0
        cboVideoFormat.Location = New System.Drawing.Point(140, 23) : cboVideoFormat.Size = New System.Drawing.Size(360, 23)
        grpVideoSettings.Controls.Add(cboVideoFormat)

        Dim lblVAudio As New System.Windows.Forms.Label()
        lblVAudio.Text = "Nhạc nền Video:" : lblVAudio.Location = New System.Drawing.Point(16, 62) : lblVAudio.Size = New System.Drawing.Size(120, 20)
        grpVideoSettings.Controls.Add(lblVAudio)

        Dim cboAudioChoice As New System.Windows.Forms.ComboBox()
        cboAudioChoice.DropDownStyle = ComboBoxStyle.DropDownList
        cboAudioChoice.Items.Add("🎵 Tự Động Theo Từng Cảnh (Epic / SciFi / Phonk / Glitch / Apple) [Khuyên dùng]")
        cboAudioChoice.Items.Add("🔇 Video Không Nhạc (Silent Video)")
        cboAudioChoice.SelectedIndex = 0
        cboAudioChoice.Location = New System.Drawing.Point(140, 59) : cboAudioChoice.Size = New System.Drawing.Size(360, 23)
        grpVideoSettings.Controls.Add(cboAudioChoice)

        Dim lblVFPS As New System.Windows.Forms.Label()
        lblVFPS.Text = "Khung hình (FPS):" : lblVFPS.Location = New System.Drawing.Point(16, 98) : lblVFPS.Size = New System.Drawing.Size(120, 20)
        grpVideoSettings.Controls.Add(lblVFPS)

        Dim cboFPS As New System.Windows.Forms.ComboBox()
        cboFPS.DropDownStyle = ComboBoxStyle.DropDownList
        cboFPS.Items.Add("30 FPS (Mượt Mà & Xuất Siêu Tốc) [Khuyên dùng]")
        cboFPS.Items.Add("60 FPS (Siêu Mượt Chuẩn Cinema)")
        cboFPS.SelectedIndex = 0
        cboFPS.Location = New System.Drawing.Point(140, 95) : cboFPS.Size = New System.Drawing.Size(360, 23)
        grpVideoSettings.Controls.Add(cboFPS)

        Dim chkOpenFolder As New System.Windows.Forms.CheckBox()
        chkOpenFolder.Text = "Tự động mở thư mục chứa video MP4 khi xuất xong"
        chkOpenFolder.Checked = True
        chkOpenFolder.Location = New System.Drawing.Point(16, 135) : chkOpenFolder.Size = New System.Drawing.Size(460, 22)
        grpVideoSettings.Controls.Add(chkOpenFolder)

        Dim chkCleanup As New System.Windows.Forms.CheckBox()
        chkCleanup.Text = "Tự động dọn dẹp file ảnh tạm PNG sau khi hoàn tất đóng gói"
        chkCleanup.Checked = True
        chkCleanup.Location = New System.Drawing.Point(16, 165) : chkCleanup.Size = New System.Drawing.Size(460, 22)
        grpVideoSettings.Controls.Add(chkCleanup)

        ' ======================================================================
        ' BOTTOM BUTTONS (CỐ ĐỊNH BÊN DƯỚI TẤT CẢ TABS - 2 HÀNG THAO TÁC)
        ' ======================================================================
        ' Hàng 1 (Y: 726): Thao tác cho Cảnh đang chọn
        Dim btnRunTab As New System.Windows.Forms.Button()
        btnRunTab.Text = "▶ CHẠY THỬ CẢNH (ESC)"
        btnRunTab.Location = New System.Drawing.Point(14, 726)
        btnRunTab.Size = New System.Drawing.Size(255, 40)
        btnRunTab.BackColor = System.Drawing.Color.FromArgb(20, 120, 60)
        btnRunTab.ForeColor = System.Drawing.Color.White
        btnRunTab.FlatStyle = FlatStyle.Flat
        btnRunTab.Font = New System.Drawing.Font("Segoe UI", 9.0!, FontStyle.Bold)
        form.Controls.Add(btnRunTab)

        Dim btnExportTab As New System.Windows.Forms.Button()
        btnExportTab.Text = "► XUẤT TIKTOK CẢNH NÀY (9:16)"
        btnExportTab.Location = New System.Drawing.Point(275, 726)
        btnExportTab.Size = New System.Drawing.Size(245, 40)
        btnExportTab.BackColor = System.Drawing.Color.FromArgb(142, 36, 170) ' TikTok Purple
        btnExportTab.ForeColor = System.Drawing.Color.White
        btnExportTab.FlatStyle = FlatStyle.Flat
        btnExportTab.Font = New System.Drawing.Font("Segoe UI", 9.0!, FontStyle.Bold)
        form.Controls.Add(btnExportTab)

        Dim btnClose As New System.Windows.Forms.Button()
        btnClose.Text = "ĐÓNG"
        btnClose.Location = New System.Drawing.Point(526, 726)
        btnClose.Size = New System.Drawing.Size(70, 85)
        btnClose.BackColor = System.Drawing.Color.FromArgb(235, 238, 242)
        btnClose.FlatStyle = FlatStyle.Flat
        btnClose.Font = New System.Drawing.Font("Segoe UI", 9.0!, FontStyle.Bold)
        form.Controls.Add(btnClose)

        ' Hàng 2 (Y: 771): Thao tác cho Ghép Phim Master
        Dim btnRunMaster As New System.Windows.Forms.Button()
        btnRunMaster.Text = "▶ CHẠY GHÉP PHIM LIÊN HOÀN (ESC)"
        btnRunMaster.Location = New System.Drawing.Point(14, 771)
        btnRunMaster.Size = New System.Drawing.Size(255, 40)
        btnRunMaster.BackColor = System.Drawing.Color.FromArgb(30, 60, 110)
        btnRunMaster.ForeColor = System.Drawing.Color.White
        btnRunMaster.FlatStyle = FlatStyle.Flat
        btnRunMaster.Font = New System.Drawing.Font("Segoe UI", 9.0!, FontStyle.Bold)
        form.Controls.Add(btnRunMaster)

        Dim btnExportMaster As New System.Windows.Forms.Button()
        btnExportMaster.Text = "► XUẤT TIKTOK GHÉP MASTER (9:16)"
        btnExportMaster.Location = New System.Drawing.Point(275, 771)
        btnExportMaster.Size = New System.Drawing.Size(245, 40)
        btnExportMaster.BackColor = System.Drawing.Color.FromArgb(15, 76, 129) ' Deep Master Blue
        btnExportMaster.ForeColor = System.Drawing.Color.White
        btnExportMaster.FlatStyle = FlatStyle.Flat
        btnExportMaster.Font = New System.Drawing.Font("Segoe UI", 9.0!, FontStyle.Bold)
        form.Controls.Add(btnExportMaster)

        AddHandler btnClose.Click, Sub(s As Object, e As EventArgs)
            form.Close()
        End Sub

        Dim applySettings01 As Action = Sub()
            Select Case cboCorner.SelectedIndex
                Case 1 : s01.CornerMode = "FRONT_RIGHT"
                Case 2 : s01.CornerMode = "BACK_RIGHT"
                Case 3 : s01.CornerMode = "BACK_LEFT"
                Case Else : s01.CornerMode = "FRONT_LEFT"
            End Select

            If radBottom.Checked Then
                s01.ViewAngleMode = "34_BOTTOM"
            ElseIf radLevel.Checked Then
                s01.ViewAngleMode = "34_LEVEL"
            Else
                s01.ViewAngleMode = "34_TOP"
            End If

            s01.DurationSeconds = CDbl(numDur.Value)
            s01.SpeedMultiplier = CDbl(numSpeed.Value)
            s01.StartDistanceScale = CDbl(numDist.Value)
            s01.EndDistanceScale = CDbl(numDistE.Value)
            s01.SwoopCurvature = CDbl(numCurve.Value)
            s01.FOVStart = CDbl(numFovS.Value)
            s01.FOVEnd = CDbl(numFovE.Value)
            s01.BankStart = CDbl(numBankS.Value)
            s01.BankEnd = CDbl(numBankE.Value)
            s01.HoldSeconds = CDbl(numHold.Value)
            s01.EnableFlyOut = chkFlyOut.Checked
            s01.FlyOutDuration = CDbl(numDurOut.Value)
        End Sub

        Dim applySettings02 As Action = Sub()
            Select Case cboCornerS02.SelectedIndex
                Case 1 : s02.CornerStart = "FRONT_LEFT"
                Case 2 : s02.CornerStart = "FRONT_RIGHT"
                Case 3 : s02.CornerStart = "BACK_RIGHT"
                Case 4 : s02.CornerStart = "BACK_LEFT"
                Case Else : s02.CornerStart = "AUTO_C1"
            End Select

            Select Case cboCornerE02.SelectedIndex
                Case 1 : s02.CornerEnd = "FRONT_RIGHT"
                Case 2 : s02.CornerEnd = "BACK_RIGHT"
                Case 3 : s02.CornerEnd = "BACK_LEFT"
                Case Else : s02.CornerEnd = "FRONT_LEFT"
            End Select

            If radBottom02.Checked Then
                s02.ViewAngleModeEnd = "34_BOTTOM"
            ElseIf radLevel02.Checked Then
                s02.ViewAngleModeEnd = "34_LEVEL"
            Else
                s02.ViewAngleModeEnd = "34_TOP"
            End If

            s02.TrajectoryMode = If(radStraight02.Checked, "STRAIGHT", "CURVED")
            s02.SwoopCurvature = CDbl(numCurve02.Value)

            s02.DurationSeconds = CDbl(numDur02.Value)
            s02.SpeedMultiplier = CDbl(numSpeed02.Value)
            s02.StartDistanceScale = CDbl(numDistS02.Value)
            s02.EndDistanceScale = CDbl(numDistE02.Value)
            s02.FOVStart = 50.0
            s02.FOVEnd = 50.0
            Select Case cboEasing02.SelectedIndex
                Case 1 : s02.EasingMode = "EASE_IN"
                Case 2 : s02.EasingMode = "EASE_IN_OUT"
                Case 3 : s02.EasingMode = "LINEAR"
                Case Else : s02.EasingMode = "EASE_OUT"
            End Select
            s02.BankStart = CDbl(numBankS02.Value)
            s02.BankEnd = CDbl(numBankE02.Value)
            s02.HoldSeconds = CDbl(numHold02.Value)
        End Sub

        Dim applySettings03 As Action = Sub()
            Select Case cboTarget03.SelectedIndex
                Case 0 : s03.FocusMode = "CORNER_1"
                Case 1 : s03.FocusMode = "CORNER_2"
                Case 2 : s03.FocusMode = "CORNER_3"
                Case 3 : s03.FocusMode = "CORNER_4"
                Case 4 : s03.FocusMode = "FRONT_FACADE"
                Case 5 : s03.FocusMode = "BACK_FACADE"
                Case 6 : s03.FocusMode = "SKID_CENTER"
                Case 7 : s03.FocusMode = "CUSTOM_PICK"
                Case Else : s03.FocusMode = "CORNER_1"
            End Select

            If radBottom03.Checked Then
                s03.ViewAngleMode = "34_BOTTOM"
            ElseIf radLevel03.Checked Then
                s03.ViewAngleMode = "34_LEVEL"
            Else
                s03.ViewAngleMode = "34_TOP"
            End If

            Select Case cboCycle03.SelectedIndex
                Case 1 : s03.CycleMode = "HALF_CYCLE"
                Case 2 : s03.CycleMode = "2_CYCLES"
                Case Else : s03.CycleMode = "FULL_CYCLE"
            End Select

            s03.SwayPercent = CDbl(numSway03.Value)
            s03.NearDistanceScale = CDbl(numNearDist03.Value)
            s03.FarDistanceScale = CDbl(numFarDist03.Value)

            s03.DurationSeconds = CDbl(numDur03.Value)
            s03.SpeedMultiplier = CDbl(numSpeed03.Value)

            Select Case cboEasing03.SelectedIndex
                Case 1 : s03.EasingMode = "EASE_OUT"
                Case 2 : s03.EasingMode = "EASE_IN"
                Case 3 : s03.EasingMode = "LINEAR"
                Case Else : s03.EasingMode = "EASE_IN_OUT"
            End Select

            s03.BankStart = CDbl(numBankS03.Value)
            s03.BankEnd = CDbl(numBankE03.Value)
            s03.VerticalBobPercent = CDbl(numBob03.Value)
            s03.HoldSeconds = CDbl(numHold03.Value)
        End Sub

        ' Xử lý nút CHẠY THỬ CẢNH ĐANG CHỌN
        AddHandler btnRunTab.Click, Sub(s As Object, e As EventArgs)
            applySettings01()
            applySettings02()
            applySettings03()
            applySettings04()
            applySettings05()

            form.Visible = False
            Try
                Select Case tabStudio.SelectedIndex
                    Case 0
                        ExecuteShot01(oDoc, s01)
                    Case 1
                        ExecuteShot02(oDoc, s02, s01, model)
                    Case 2
                        ExecuteShot03(oDoc, s03, s02, s01, model, heroes)
                    Case 3
                        ExecuteShot04(oDoc, s04, s03, s02, s01, model, heroes)
                    Case 4
                        ExecuteShot05(oDoc, s05, s04, s03, s02, s01, model, heroes)
                    Case Else
                        MessageBox.Show("Vui lòng chọn Cảnh 1 đến Cảnh 5 để chạy thử.", "WT3D WhipCam", MessageBoxButtons.OK, MessageBoxIcon.Information)
                End Select
            Catch ex As Exception
                MessageBox.Show("Lỗi: " & ex.Message, "WhipCam Error", MessageBoxButtons.OK, MessageBoxIcon.Error)
            Finally
                form.Visible = True
            End Try
        End Sub

        ' Xử lý nút CHẠY GHÉP PHIM (LIÊN HOÀN CÁC CẢNH ĐƯỢC CHỌN)
        AddHandler btnRunMaster.Click, Sub(s As Object, e As EventArgs)
            applySettings01()
            applySettings02()
            applySettings03()
            applySettings04()
            applySettings05()

            ' Khi ghép phim liên hoàn: Cảnh 1 không bay ra xa
            Dim oldFlyOut As Boolean = s01.EnableFlyOut
            s01.EnableFlyOut = False

            form.Visible = False
            Try
                Dim lastEye As Vec3 = Nothing
                Dim lastTarget As Vec3 = Nothing
                Dim lastUp As Vec3 = Nothing
                Dim lastFOV As Double = 50.0

                Dim aborted As Boolean = False

                ' 1. Cảnh 1
                If chkM01.Checked Then
                    If Not ExecuteShot01(oDoc, s01, lastEye, lastTarget, lastUp, lastFOV) Then aborted = True
                End If

                ' 2. Cảnh 2
                If Not aborted AndAlso chkM02.Checked Then
                    Dim nEye As Vec3 = Nothing : Dim nTarget As Vec3 = Nothing : Dim nUp As Vec3 = Nothing : Dim nFOV As Double = 50.0
                    If Not ExecuteShot02(oDoc, s02, s01, model, lastEye, lastTarget, nEye, nTarget, nUp, nFOV) Then aborted = True
                    lastEye = nEye : lastTarget = nTarget : lastUp = nUp : lastFOV = nFOV
                End If

                ' 3. Cảnh 3
                If Not aborted AndAlso chkM03.Checked Then
                    Dim nEye As Vec3 = Nothing : Dim nTarget As Vec3 = Nothing : Dim nUp As Vec3 = Nothing : Dim nFOV As Double = 50.0
                    If Not ExecuteShot03(oDoc, s03, s02, s01, model, heroes, lastEye, lastTarget, nEye, nTarget, nUp, nFOV) Then aborted = True
                    lastEye = nEye : lastTarget = nTarget : lastUp = nUp : lastFOV = nFOV
                End If

                ' 4. Cảnh 4
                If Not aborted AndAlso chkM04.Checked Then
                    Dim nEye As Vec3 = Nothing : Dim nTarget As Vec3 = Nothing : Dim nUp As Vec3 = Nothing : Dim nFOV As Double = 50.0
                    If Not ExecuteShot04(oDoc, s04, s03, s02, s01, model, heroes, lastEye, lastTarget, nEye, nTarget, nUp, nFOV) Then aborted = True
                    lastEye = nEye : lastTarget = nTarget : lastUp = nUp : lastFOV = nFOV
                End If

                ' 5. Cảnh 5
                If Not aborted AndAlso chkM05.Checked Then
                    Dim nEye As Vec3 = Nothing : Dim nTarget As Vec3 = Nothing : Dim nUp As Vec3 = Nothing : Dim nFOV As Double = 50.0
                    ExecuteShot05(oDoc, s05, s04, s03, s02, s01, model, heroes, lastEye, lastTarget, nEye, nTarget, nUp, nFOV)
                End If
            Catch ex As Exception
                MessageBox.Show("Lỗi Ghép Phim: " & ex.Message, "WhipCam Error", MessageBoxButtons.OK, MessageBoxIcon.Error)
            Finally
                s01.EnableFlyOut = oldFlyOut
                form.Visible = True
            End Try
        End Sub

        ' Hàm lấy định dạng video chuỗi
        Dim getVideoFormatCode As Func(Of String) = Function()
            Select Case cboVideoFormat.SelectedIndex
                Case 0 : Return "native_916"
                Case 1 : Return "tiktok_blur_916"
                Case 2 : Return "widescreen_169"
                Case Else : Return "native_916"
            End Select
        End Function

        ' Hàm lấy FPS số
        Dim getVideoFPS As Func(Of Integer) = Function()
            If cboFPS.SelectedIndex = 1 Then Return 60 Else Return 30
        End Function

        ' Hàm lấy AudioMode
        Dim getVideoAudioMode As Func(Of String) = Function()
            If cboAudioChoice.SelectedIndex = 1 Then Return "none" Else Return "auto"
        End Function

        ' Xử lý nút XUẤT VIDEO TIKTOK CẢNH ĐANG CHỌN
        AddHandler btnExportTab.Click, Sub(s As Object, e As EventArgs)
            applySettings01()
            applySettings02()
            applySettings03()
            applySettings04()
            applySettings05()

            If tabStudio.SelectedIndex > 4 Then
                MessageBox.Show("Vui lòng chọn Cảnh 1 đến Cảnh 5 trước khi bấm xuất video cảnh lẻ.", "WT3D Video Exporter", MessageBoxButtons.OK, MessageBoxIcon.Information)
                Return
            End If

            RunExportPipeline(False, oDoc, s01, s02, s03, s04, s05, model, heroes, _
                              tabStudio.SelectedIndex, chkM01.Checked, chkM02.Checked, chkM03.Checked, chkM04.Checked, chkM05.Checked, _
                              getVideoFormatCode(), getVideoFPS(), getVideoAudioMode(), chkOpenFolder.Checked, chkCleanup.Checked, form)
        End Sub

        ' Xử lý nút XUẤT VIDEO TIKTOK GHÉP MASTER
        AddHandler btnExportMaster.Click, Sub(s As Object, e As EventArgs)
            applySettings01()
            applySettings02()
            applySettings03()
            applySettings04()
            applySettings05()

            If Not (chkM01.Checked OrElse chkM02.Checked OrElse chkM03.Checked OrElse chkM04.Checked OrElse chkM05.Checked) Then
                MessageBox.Show("Vui lòng chọn ít nhất một Cảnh tham gia ghép phim.", "WT3D Video Exporter", MessageBoxButtons.OK, MessageBoxIcon.Warning)
                Return
            End If

            RunExportPipeline(True, oDoc, s01, s02, s03, s04, s05, model, heroes, _
                              tabStudio.SelectedIndex, chkM01.Checked, chkM02.Checked, chkM03.Checked, chkM04.Checked, chkM05.Checked, _
                              getVideoFormatCode(), getVideoFPS(), getVideoAudioMode(), chkOpenFolder.Checked, chkCleanup.Checked, form)
        End Sub

        tabStudio.SelectedIndex = activeTabIndex
        form.ShowDialog()

        If formPendingAction = "INTERACTIVE_PICK" Then
            ' Form đã đóng hoàn toàn, Inventor 100% tự do tương tác
            Dim pickMore As Boolean = True
            Do
                Try
                    oApp.StatusBarText = "WT3D: Bấm chuột vào chi tiết cần soi trên 3D (Nhấn ESC để hoàn tất)..."
                    Dim pickedObj As Object = oApp.CommandManager.Pick(SelectionFilterEnum.kAssemblyLeafOccurrenceFilter, "Bấm chuột vào chi tiết cần soi trong Cảnh 4 (Nhấn ESC để hoàn tất)...")

                    If pickedObj IsNot Nothing Then
                        Dim occ As ComponentOccurrence = TryCast(pickedObj, ComponentOccurrence)
                        If occ IsNot Nothing Then
                            Dim b As Box = occ.RangeBox
                            Dim pt As New Vec3((b.MinPoint.X + b.MaxPoint.X) * 0.5, (b.MinPoint.Y + b.MaxPoint.Y) * 0.5, (b.MinPoint.Z + b.MaxPoint.Z) * 0.5)
                            s04.CustomPickPoints.Add(pt)
                            s04.PointsMode = "CUSTOM_PICK"
                            customPointNames.Add(occ.Name)

                            ' Đồng thời ghi nhận vector hướng nhìn của Camera hiện tại trong Inventor
                            Dim curCamNow As Inventor.Camera = oApp.ActiveView.Camera
                            Dim cEye As New Vec3(curCamNow.Eye.X, curCamNow.Eye.Y, curCamNow.Eye.Z)
                            Dim cTgt As New Vec3(curCamNow.Target.X, curCamNow.Target.Y, curCamNow.Target.Z)
                            Dim appDir As Vec3 = (cEye - cTgt).Normalize()
                            If appDir.Length() < 1E-5 Then appDir = New Vec3(-0.7071, 0.5, -0.7071).Normalize()
                            s04.CustomApproachVectors.Add(appDir)

                            Dim ask As DialogResult = MessageBox.Show(String.Format("✔ Đã lấy: '{0}' (Điểm thứ {1})." & vbCrLf & vbCrLf & "Bạn có muốn click chọn thêm điểm tiếp theo không?", occ.Name, s04.CustomPickPoints.Count), "WT3D Chọn Điểm Thành Công", MessageBoxButtons.YesNo, MessageBoxIcon.Question)
                            If ask = DialogResult.No Then
                                pickMore = False
                            End If
                        Else
                            pickMore = False
                        End If
                    Else
                        pickMore = False
                    End If
                Catch ex As Exception
                    pickMore = False
                End Try
            Loop While pickMore

            ' Tự động lưu vĩnh viễn (Auto-Save)
            If s04.CustomPickPoints.Count > 0 Then
                SavePointsToStorage(oDoc, s04.CustomPickPoints, s04.CustomApproachVectors, customPointNames)
            End If

            oApp.StatusBarText = ""
            formPendingAction = ""
            keepStudioRunning = True
        Else
            keepStudioRunning = False
        End If
    Loop While keepStudioRunning

    End Sub

End Class
