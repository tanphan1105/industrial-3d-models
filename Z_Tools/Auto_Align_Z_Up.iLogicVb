' ======================================================================
' Auto_Align_Z_Up (iLogic Rule) - Refactored for Batch Automation
' Smart coordinate alignment: Auto-detect longest axis → rotate to Z-Up
' 
' REFACTOR HIGHLIGHTS (AUTODESK STANDARD):
' 1. Global Assembly-Level Transform (prevents occurrence drift)
' 2. No forced grounding (preserves batch flexibility)
' 3. Deterministic mapping (no heuristic guessing)
' 4. Clean ViewCube separation
' ======================================================================

AddReference "System.Windows.Forms"
AddReference "System.Private.Windows.Core"

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Try
            Dim oDoc As AssemblyDocument = TryCast(ThisDoc.Document, AssemblyDocument)
            If oDoc Is Nothing Then
                ThisApplication.StatusBarText = "⚠️ Ignore - Not an Assembly (.iam)"
                Return
            End If

            Dim oDef As AssemblyComponentDefinition = oDoc.ComponentDefinition

            ' Force Inventor setting: Place and ground first component at origin
            Try
                ThisApplication.AssemblyOptions.PlaceAndGroundFirstComponentAtOrigin = True
            Catch : End Try

            If oDef.Occurrences.Count = 0 Then Return

            ' Detect mirrored components to avoid constraint solver tearing the assembly apart during transform overrides
            For Each occ As ComponentOccurrence In oDef.Occurrences
                    If CheckEscape() Then
                        ThisApplication.StatusBarText = "🛑 ĐÃ DỪNG VÒNG LẶP THEO LỆNH (GIỮ PHÍM ESC)!"
                        Exit Sub
                    End If
                    SafeYield(10)
                If Not occ.Suppressed AndAlso occ.Name.ToUpper().Contains("_MIR") Then
                    ThisApplication.StatusBarText = "⚠️ Skipped Z-Up Alignment: Mirrored components detected."
                    Return
                End If
            Next

            ' Skip Z-Up alignment for inline accessories (valves, Y-strainers, unions, etc.)
            ' to preserve the designer's centering of the pipe centerline at the coordinate origin.
            Dim docNameLower As String = System.IO.Path.GetFileName(oDoc.FullFileName).ToLower()
            If docNameLower.Contains("inline") OrElse docNameLower.StartsWith("v") OrElse docNameLower.StartsWith("y") OrElse _
               docNameLower.Contains("racco") OrElse docNameLower.Contains("union") OrElse docNameLower.Contains("strainer") Then
                ThisApplication.StatusBarText = "⚠️ Skipped Z-Up Alignment: Inline accessory detected."
                Return
            End If

            Dim tg As TransientGeometry = ThisApplication.TransientGeometry

            ' --- STEP 1: CACHE GROUNDED STATES & UNGROUND ALL ---
            ' Grounded=True breaks transforms in batch. We unground before moving.
            Dim groundedStates As New Dictionary(Of ComponentOccurrence, Boolean)
            For Each occ As ComponentOccurrence In oDef.Occurrences
                    If CheckEscape() Then
                        ThisApplication.StatusBarText = "🛑 ĐÃ DỪNG VÒNG LẶP THEO LỆNH (GIỮ PHÍM ESC)!"
                        Exit Sub
                    End If
                    SafeYield(10)
                If Not occ.Suppressed Then
                    groundedStates.Add(occ, occ.Grounded)
                    occ.Grounded = False
                End If
            Next

            ' --- STEP 2: MEASURE GLOBAL BOUNDING BOX ---
            Dim minX As Double = 1.0E+15, minY As Double = 1.0E+15, minZ As Double = 1.0E+15
            Dim maxX As Double = -1.0E+15, maxY As Double = -1.0E+15, maxZ As Double = -1.0E+15
            Dim validBox As Boolean = False

            For Each occ As ComponentOccurrence In oDef.Occurrences
                    If CheckEscape() Then
                        ThisApplication.StatusBarText = "🛑 ĐÃ DỪNG VÒNG LẶP THEO LỆNH (GIỮ PHÍM ESC)!"
                        Exit Sub
                    End If
                    SafeYield(10)
                If Not occ.Suppressed Then
                    Try
                        Dim rBox As Box = occ.RangeBox
                        If rBox IsNot Nothing Then
                            If rBox.MinPoint.X < minX Then minX = rBox.MinPoint.X
                            If rBox.MinPoint.Y < minY Then minY = rBox.MinPoint.Y
                            If rBox.MinPoint.Z < minZ Then minZ = rBox.MinPoint.Z
                            If rBox.MaxPoint.X > maxX Then maxX = rBox.MaxPoint.X
                            If rBox.MaxPoint.Y > maxY Then maxY = rBox.MaxPoint.Y
                            If rBox.MaxPoint.Z > maxZ Then maxZ = rBox.MaxPoint.Z
                            validBox = True
                        End If
                    Catch : End Try
                End If
            Next

            If Not validBox Then Return

            Dim spanX As Double = maxX - minX
            Dim spanY As Double = maxY - minY
            Dim spanZ As Double = maxZ - minZ

            ' --- STEP 3: CONSTRUCT GLOBAL ROTATION MATRIX (DETERMINISTIC) ---
            ' We map the longest axis mathematically to +Z.
            Dim globalRot As Matrix = tg.CreateMatrix()
            Dim longestAxis As String = "Z"

            If spanX >= spanY AndAlso spanX >= spanZ Then
                ' X is longest → map +X to +Z (Rotate -90° around Y)
                longestAxis = "X"
                globalRot.SetToRotation(-Math.PI / 2, tg.CreateVector(0, 1, 0), tg.CreatePoint(0, 0, 0))
            ElseIf spanY >= spanX AndAlso spanY >= spanZ Then
                ' Y is longest → map +Y to +Z (Rotate +90° around X)
                longestAxis = "Y"
                globalRot.SetToRotation(Math.PI / 2, tg.CreateVector(1, 0, 0), tg.CreatePoint(0, 0, 0))
            Else
                longestAxis = "Z"
            End If

            ' Apply global rotation to all top-level occurrences
            If longestAxis <> "Z" Then
                For Each occ As ComponentOccurrence In oDef.Occurrences
                    If CheckEscape() Then
                        ThisApplication.StatusBarText = "🛑 ĐÃ DỪNG VÒNG LẶP THEO LỆNH (GIỮ PHÍM ESC)!"
                        Exit Sub
                    End If
                    SafeYield(10)
                    If Not occ.Suppressed Then
                        Try
                            Dim mat As Matrix = occ.Transformation
                            mat.PreMultiplyBy(globalRot)
                            occ.Transformation = mat
                        Catch : End Try
                    End If
                Next
                oDoc.Update()
            End If

            ' --- STEP 4: RE-MEASURE AFTER ROTATION ---
            minX = 1.0E+15 : minY = 1.0E+15 : minZ = 1.0E+15
            maxX = -1.0E+15 : maxY = -1.0E+15 : maxZ = -1.0E+15

            For Each occ As ComponentOccurrence In oDef.Occurrences
                    If CheckEscape() Then
                        ThisApplication.StatusBarText = "🛑 ĐÃ DỪNG VÒNG LẶP THEO LỆNH (GIỮ PHÍM ESC)!"
                        Exit Sub
                    End If
                    SafeYield(10)
                If Not occ.Suppressed Then
                    Try
                        Dim rBox As Box = occ.RangeBox
                        If rBox IsNot Nothing Then
                            If rBox.MinPoint.X < minX Then minX = rBox.MinPoint.X
                            If rBox.MinPoint.Y < minY Then minY = rBox.MinPoint.Y
                            If rBox.MinPoint.Z < minZ Then minZ = rBox.MinPoint.Z
                            If rBox.MaxPoint.X > maxX Then maxX = rBox.MaxPoint.X
                            If rBox.MaxPoint.Y > maxY Then maxY = rBox.MaxPoint.Y
                            If rBox.MaxPoint.Z > maxZ Then maxZ = rBox.MaxPoint.Z
                        End If
                    Catch : End Try
                End If
            Next

            ' --- STEP 5: GLOBAL TRANSLATION (CENTER X,Y AND BOTTOM Z=0) ---
            Dim cx As Double = (maxX + minX) / 2.0
            Dim cy As Double = (maxY + minY) / 2.0
            Dim bottomZ As Double = minZ

            ' Heuristic: If model is already close to X/Y origin (within 10cm / 100mm),
            ' preserve the designer's centering and ignore minor offsets from asymmetric attachments (gauges, nozzles)
            If Math.Abs(cx) < 10.0 Then cx = 0.0
            If Math.Abs(cy) < 10.0 Then cy = 0.0

            For Each occ As ComponentOccurrence In oDef.Occurrences
                    If CheckEscape() Then
                        ThisApplication.StatusBarText = "🛑 ĐÃ DỪNG VÒNG LẶP THEO LỆNH (GIỮ PHÍM ESC)!"
                        Exit Sub
                    End If
                    SafeYield(10)
                If Not occ.Suppressed Then
                    Try
                        Dim mat As Matrix = occ.Transformation
                        mat.Cell(1, 4) = mat.Cell(1, 4) - cx
                        mat.Cell(2, 4) = mat.Cell(2, 4) - cy
                        mat.Cell(3, 4) = mat.Cell(3, 4) - bottomZ
                        occ.Transformation = mat

                        ' Restore original grounded state instead of forcing True
                        If groundedStates.ContainsKey(occ) Then
                            occ.Grounded = groundedStates(occ)
                        End If
                    Catch : End Try
                End If
            Next
            oDoc.Update()

            ' --- STEP 6: POST-ROTATION VALIDATION (CENTER OF MASS HEURISTIC) ---
            ' For most tanks/filters, the heavy base is at the bottom.
            ' If the Center of Mass Z is in the top half of the bounding box,
            ' it is highly likely upside down, so we flip it 180° around X.
            Try
                Dim comZ As Double = oDef.MassProperties.CenterOfMass.Z
                Dim boxCenterZ As Double = (maxZ - minZ) / 2.0
                ' Skip flipping for Pumps because the heavy motor is naturally at the top!
                Dim isPumpDevice As Boolean = docNameLower.Contains("bom") OrElse docNameLower.Contains("pump") OrElse docNameLower.Contains("bwi")

                ' Also check custom property
                Try
                    Dim userEqType As String = oDoc.PropertySets.Item("Inventor User Defined Properties").Item("OMW_EQUIPMENT_TYPE").Value.Trim().ToLower()
                    if userEqType = "pump" Then isPumpDevice = True
                Catch : End Try

                If Not isPumpDevice AndAlso comZ > boxCenterZ * 1.1 Then ' 10% threshold to avoid false flips on symmetric parts
                    ' Flip 180 degrees around X to correct the upside-down state
                    Dim flipRot As Matrix = tg.CreateMatrix()
                    flipRot.SetToRotation(Math.PI, tg.CreateVector(1, 0, 0), tg.CreatePoint(0, 0, (maxZ - minZ) / 2.0))

                    For Each occ As ComponentOccurrence In oDef.Occurrences
                    If CheckEscape() Then
                        ThisApplication.StatusBarText = "🛑 ĐÃ DỪNG VÒNG LẶP THEO LỆNH (GIỮ PHÍM ESC)!"
                        Exit Sub
                    End If
                    SafeYield(10)
                        If Not occ.Suppressed Then
                            Dim mat As Matrix = occ.Transformation
                            mat.PreMultiplyBy(flipRot)
                            occ.Transformation = mat
                        End If
                    Next
                    oDoc.Update()
                End If
            Catch : End Try

            ' --- STEP 7: VIEWCUBE SETUP (XY = BOTTOM) ---
            Try
                Dim oCam As Camera = ThisApplication.ActiveView.Camera

                oCam.Target = tg.CreatePoint(0, 0, 0)
                oCam.Eye = tg.CreatePoint(0, 0, 100)
                oCam.UpVector = tg.CreateUnitVector(0, 1, 0)
                oCam.ApplyWithoutTransition()
                ThisApplication.ActiveView.SetCurrentAsTop()

                oCam.Target = tg.CreatePoint(0, 0, 0)
                oCam.Eye = tg.CreatePoint(0, -100, 0)
                oCam.UpVector = tg.CreateUnitVector(0, 0, 1)
                oCam.ApplyWithoutTransition()
                Try
                    ThisApplication.ActiveView.SetCurrentAsFront()
                Catch : End Try

                oCam.Target = tg.CreatePoint(0, 0, (maxZ - bottomZ) / 2.0)
                Dim dist As Double = Math.Max(maxX - minX, Math.Max(maxY - minY, maxZ - bottomZ)) * 2
                If dist < 1 Then dist = 100
                oCam.Eye = tg.CreatePoint(dist, -dist, dist)
                oCam.UpVector = tg.CreateUnitVector(0, 0, 1)
                oCam.Fit()
                oCam.ApplyWithoutTransition()

                ThisApplication.ActiveView.SetCurrentAsHome()
            Catch : End Try

            ' --- STEP 8: DISPLAY SETTINGS (SHADED WITH EDGES + WORK PLANES) ---
            Try
                ' 8.1 Set Display Mode to Shaded With Edges
                ThisApplication.ActiveView.DisplayMode = DisplayModeEnum.kShadedWithEdgesRendering

                ' 8.2 Object Visibility: Only Work Planes ON, others OFF
                Dim objVis As ObjectVisibility = oDoc.ObjectVisibility
                objVis.OriginWorkPlanes = True
                objVis.UserWorkPlanes = True

                objVis.OriginWorkAxes = False
                objVis.UserWorkAxes = False
                objVis.OriginWorkPoints = False
                objVis.UserWorkPoints = False
                objVis.Sketches = False
                objVis.Sketches3D = False
            Catch : End Try

            ThisApplication.CommandManager.ControlDefinitions.Item("AppZoomAllCmd").Execute()
            ThisApplication.StatusBarText = "✅ Z-Up Aligned | " & longestAxis & "→Z | Grounding Restored | Shaded+Edges | Planes ON"

        Catch ex As Exception
            ThisApplication.StatusBarText = "❌ Alignment Error: " & ex.Message
        End Try
    End Sub
End Class
