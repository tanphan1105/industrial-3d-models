AddReference "PresentationCore"
AddReference "WindowsBase"
AddReference "System.Drawing"
AddReference "System.Private.Windows.GdiPlus"
AddReference "System.Windows.Forms"
AddReference "System.Private.Windows.Core"

Imports System.Windows.Input

' ==============================================================================
' CAM_1_YT_CinematicWalkthrough.iLogicVb
' Mục đích: Video ngang 16:9 cho YouTube/Fab. Góc máy Tele chậm rãi, hoành tráng.
' ==============================================================================

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Dim oApp As Inventor.Application = ThisApplication
        Dim oDoc As Document = oApp.ActiveDocument
        Dim oView As Inventor.View = oApp.ActiveView
        Dim oCam As Camera = oView.Camera
        Dim tg As TransientGeometry = oApp.TransientGeometry

        If oDoc.DocumentType <> DocumentTypeEnum.kAssemblyDocumentObject And oDoc.DocumentType <> DocumentTypeEnum.kPartDocumentObject Then Exit Sub

        ' --- CẤU HÌNH ĐỘ PHÂN GIẢI 4K ULTRA-HD (3840 x 2160 FOR YOUTUBE 16:9) ---
        Dim renderW As Integer = 3840
        Dim renderH As Integer = 2160

        ' ============================================================
        ' 🧠 AUTO-GENERATE SEO METADATA (ZERO-TOUCH - Chạy trước render)
        ' Đảm bảo Dashboard_SEO & Z_Copy_Paste_SEO_Data.txt luôn mới nhất
        ' ============================================================
        Dim isBatch As Boolean = False
        Try : isBatch = SharedVariable("BatchMode") : Catch : End Try

        If Not isBatch Then
            ThisApplication.StatusBarText = "🧠 CAM 1: Generating SEO Metadata..."
            Try : iLogicVb.RunExternalRule("d:\WT3D_Project\Z_Tools\Auto_SEO_Metadata_Engine.iLogicVb") : Catch : End Try
        End If
        ThisApplication.StatusBarText = "🎥 CAM 1: Starting render..."
        ' ============================================================

        ' --- LƯU TRẠNG THÁI CAMERA GỐC ---
        Dim oTg2 As TransientGeometry = ThisApplication.TransientGeometry
        Dim orgEyeX = oCam.Eye.X, orgEyeY = oCam.Eye.Y, orgEyeZ = oCam.Eye.Z
        Dim orgTgx = oCam.Target.X, orgTgy = oCam.Target.Y, orgTgz = oCam.Target.Z
        Dim orgUpX = oCam.UpVector.X, orgUpY = oCam.UpVector.Y, orgUpZ = oCam.UpVector.Z
        Dim orgPersp = oCam.Perspective
        Dim orgPerspAng = 0.0
        Try
            orgPerspAng = oCam.PerspectiveAngle
        Catch
        End Try
        ' -----------------------------------

        Dim rb = oDoc.ComponentDefinition.RangeBox
        Dim cx = (rb.MinPoint.X + rb.MaxPoint.X) / 2
        Dim cy = (rb.MinPoint.Y + rb.MaxPoint.Y) / 2
        Dim cz = (rb.MinPoint.Z + rb.MaxPoint.Z) / 2
        Dim dx = rb.MaxPoint.X - rb.MinPoint.X
        Dim dy = rb.MaxPoint.Y - rb.MinPoint.Y
        Dim dz = rb.MaxPoint.Z - rb.MinPoint.Z
        Dim max_dim = Math.Max(dx, Math.Max(dy, dz))

        ' --- SETUP MÔI TRƯỜNG ÁNH SÁNG & ĐỔ BÓNG ---
        Try
            oView.ShowShadows = True
            oView.ShowAmbientShadows = True
            oView.ShowObjectShadows = True
            oView.ShowGroundReflections = False
            oDoc.ActiveLightingStyle = oDoc.LightingStyles.Item("Photo Booth")
        Catch
            Try : oDoc.ActiveLightingStyle = oDoc.LightingStyles.Item("Empty Lab") : Catch : End Try
        End Try
        ' -----------------------------------------

        ' --- XUẤT VIDEO FRAMES ---
        Dim tempPath = "d:\WT3D_Project\2_Video_Renders\"
        If Not System.IO.Directory.Exists(tempPath) Then System.IO.Directory.CreateDirectory(tempPath)
        Dim saveFolder = tempPath & System.IO.Path.GetFileNameWithoutExtension(oDoc.FullFileName) & "_CAM_1"
        If Not System.IO.Directory.Exists(saveFolder) Then System.IO.Directory.CreateDirectory(saveFolder)
        Dim frameCount = 1
        ' -------------------------

        Try
            oView.DisplayMode = DisplayModeEnum.kShadedWithEdgesRendering
            oView.Update()
        Catch
        End Try

        ' ' _MUTED_BY_AI_MessageBox_Show("▶ BẤM OK ĐỂ CHẠY: CAM 1 - YOUTUBE CINEMATIC WALKTHROUGH (16:9)" & vbCrLf & "Góc máy Tele chậm rãi, chuyên nghiệp, giữ nguyên Shaded With Edges.", "Đạo Diễn B2B")

        Dim isAborted As Boolean = False
        Dim orgDispMode = oView.DisplayMode
        Try : oView.DisplayMode = DisplayModeEnum.kShadedWithEdgesRendering : oView.Update() : Catch : End Try
        oCam.Perspective = True ' Bắt đầu bằng 3/4 Perspective góc 3D chuẩn
        oCam.PerspectiveAngle = 0.52
        oCam.Apply()

        ' === SCENE 1: Close Hero Perspective Glide (35f - Robot Bolt Quintic Easing) ===
        Try : oView.DisplayMode = DisplayModeEnum.kShadedWithEdgesRendering : oView.Update() : Catch : End Try
        oCam.Perspective = True
        Dim fMax1 As Integer = 35
        For i = 1 To fMax1
            Dim fMax As Double = CDbl(fMax1)
            Dim t = i / fMax : Dim e = t * t * t * (t * (t * 6.0 - 15.0) + 10.0) ' Quintic Smoothstep
            Dim theta = Math.PI * 0.25 + (Math.PI * 0.15) * e
            Dim curR = max_dim * (0.80 - 0.25 * e)
            Dim gimbalRoll = Math.Sin(Math.PI * e) * 0.04
            oCam.Eye = tg.CreatePoint(cx + curR * Math.Cos(theta), cy + dy * 0.1, cz + curR * Math.Sin(theta))
            oCam.Target = tg.CreatePoint(cx, cy, cz)
            oCam.PerspectiveAngle = 0.52
            oCam.UpVector = tg.CreateUnitVector(gimbalRoll, 1.0, 0.0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 2: Fast 360 Flycam Sweep (45f - Dynamic Roll) ===
        Try : oView.DisplayMode = DisplayModeEnum.kShadedWithEdgesRendering : oView.Update() : Catch : End Try
        oCam.Perspective = True
        Dim fMax2 As Integer = 45
        For i = 1 To fMax2
            Dim fMax As Double = CDbl(fMax2)
            Dim t = i / fMax : Dim e = t * t * t * (t * (t * 6.0 - 15.0) + 10.0)
            Dim theta = Math.PI * 0.40 + (Math.PI * 1.6) * e
            Dim curR = max_dim * (0.75 - 0.15 * Math.Sin(Math.PI * e))
            Dim sweepY = cy + dy * 0.15
            Dim gimbalRoll = Math.Sin(Math.PI * 2.0 * e) * 0.05
            oCam.Eye = tg.CreatePoint(cx + curR * Math.Cos(theta), sweepY, cz + curR * Math.Sin(theta))
            oCam.Target = tg.CreatePoint(cx, cy, cz)
            oCam.PerspectiveAngle = 0.52
            oCam.UpVector = tg.CreateUnitVector(gimbalRoll, 1.0, 0.0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 3: Macro Push-In Close-Up (30f - Smoothstep) ===
        Try : oView.DisplayMode = DisplayModeEnum.kShadedWithEdgesRendering : oView.Update() : Catch : End Try
        Dim fMax3 As Integer = 30
        For i = 1 To fMax3
            Dim fMax As Double = CDbl(fMax3)
            Dim t = i / fMax : Dim e = t * t * t * (t * (t * 6.0 - 15.0) + 10.0)
            Dim curR = max_dim * (0.70 - 0.25 * e)
            oCam.Eye = tg.CreatePoint(cx + curR * Math.Cos(Math.PI*0.35), cy + dy*0.1, cz + curR * Math.Sin(Math.PI*0.35))
            oCam.Target = tg.CreatePoint(cx, cy, cz)
            oCam.PerspectiveAngle = 0.50
            oCam.UpVector = tg.CreateUnitVector(0, 1, 0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 4: Technical Wireframe 3/4 Orbit (30f - Smoothstep) ===
        Try : oView.DisplayMode = DisplayModeEnum.kWireframeNoHiddenEdges : oView.Update() : Catch : End Try
        Dim fMax4 As Integer = 30
        For i = 1 To fMax4
            Dim fMax As Double = CDbl(fMax4)
            Dim t = i / fMax : Dim e = t * t * t * (t * (t * 6.0 - 15.0) + 10.0)
            Dim theta = Math.PI * 0.75 + (Math.PI * 0.5) * e
            Dim curR = max_dim * 0.65
            oCam.Eye = tg.CreatePoint(cx + curR * Math.Cos(theta), cy + dy * 0.2, cz + curR * Math.Sin(theta))
            oCam.Target = tg.CreatePoint(cx, cy, cz)
            oCam.PerspectiveAngle = 0.50
            oCam.UpVector = tg.CreateUnitVector(0, 1, 0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 5: Low-Angle Upward Hero 3/4 Scan (35f - Smoothstep) ===
        Try : oView.DisplayMode = DisplayModeEnum.kShadedWithEdgesRendering : oView.Update() : Catch : End Try
        oCam.Perspective = True
        Dim fMax5 As Integer = 35
        For i = 1 To fMax5
            Dim fMax As Double = CDbl(fMax5)
            Dim t = i / fMax : Dim e = t * t * t * (t * (t * 6.0 - 15.0) + 10.0)
            Dim theta = Math.PI * 1.25 + (Math.PI * 0.40) * e
            Dim elev = -Math.PI * 0.12
            Dim curR = max_dim * 0.65
            Dim gimbalRoll = -Math.Sin(Math.PI * e) * 0.04
            oCam.Eye = tg.CreatePoint(cx + curR * Math.Cos(elev) * Math.Cos(theta), cy + curR * Math.Sin(elev) - (dy * 0.05), cz + curR * Math.Cos(elev) * Math.Sin(theta))
            oCam.Target = tg.CreatePoint(cx, cy + (dy * 0.15), cz)
            oCam.PerspectiveAngle = 0.54
            oCam.UpVector = tg.CreateUnitVector(gimbalRoll, 1.0, 0.0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 6: High-Angle Top-Left Crane 3/4 Glide (35f - Smoothstep) ===
        Try : oView.DisplayMode = DisplayModeEnum.kShadedWithEdgesRendering : oView.Update() : Catch : End Try
        Dim fMax6 As Integer = 35
        For i = 1 To fMax6
            Dim fMax As Double = CDbl(fMax6)
            Dim t = i / fMax : Dim e = t * t * t * (t * (t * 6.0 - 15.0) + 10.0)
            Dim theta = Math.PI * 1.65 + (Math.PI * 0.35) * e
            Dim elev = Math.PI * 0.22
            Dim curR = max_dim * (0.70 - 0.10 * e)
            oCam.Eye = tg.CreatePoint(cx + curR * Math.Cos(elev) * Math.Cos(theta), cy + curR * Math.Sin(elev) + (dy * 0.1), cz + curR * Math.Cos(elev) * Math.Sin(theta))
            oCam.Target = tg.CreatePoint(cx, cy, cz)
            oCam.PerspectiveAngle = 0.50
            oCam.UpVector = tg.CreateUnitVector(0, 1, 0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 7: Hero Perspective 3/4 Full Screen Finale (50f - Smoothstep) ===
        Try : oView.DisplayMode = DisplayModeEnum.kShadedWithEdgesRendering : oView.Update() : Catch : End Try
        oCam.Perspective = True
        Dim fMax7 As Integer = 50
        For i = 1 To fMax7
            Dim fMax As Double = CDbl(fMax7)
            Dim t = i / fMax : Dim e = t * t * t * (t * (t * 6.0 - 15.0) + 10.0)
            Dim theta = Math.PI * 0.25 + (Math.PI * 0.50) * e
            Dim curR = max_dim * (0.50 + 0.05 * e)
            oCam.Eye = tg.CreatePoint(cx + curR * Math.Cos(theta), cy + dy * 0.1, cz + curR * Math.Sin(theta))
            oCam.Target = tg.CreatePoint(cx, cy, cz)
            oCam.PerspectiveAngle = 0.52
            oCam.UpVector = tg.CreateUnitVector(0, 1, 0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        GoTo NormalCompletion
        AbortCamera:
            MessageBox.Show("🛑 HỦY RENDER THÀNH CÔNG! Đã dừng việc chụp ảnh và xuất FFmpeg.", "Ngắt Khẩn Cấp B2B")
            Try : oView.DisplayMode = orgDispMode : Catch : End Try
            oCam.Eye = oTg2.CreatePoint(orgEyeX, orgEyeY, orgEyeZ)
            oCam.Target = oTg2.CreatePoint(orgTgx, orgTgy, orgTgz)
            oCam.UpVector = oTg2.CreateUnitVector(orgUpX, orgUpY, orgUpZ)
            oCam.Perspective = orgPersp
            If orgPersp Then : Try : oCam.PerspectiveAngle = orgPerspAng : Catch : End Try : End If
            oCam.Apply() : oView.Update()
            Exit Sub

        NormalCompletion:
        Try : oView.DisplayMode = orgDispMode : Catch : End Try

        RestoreCamera:
        ' --- TRẢ VỀ CAMERA GỐC ---
        oCam.Eye = oTg2.CreatePoint(orgEyeX, orgEyeY, orgEyeZ)
        oCam.Target = oTg2.CreatePoint(orgTgx, orgTgy, orgTgz)
        oCam.UpVector = oTg2.CreateUnitVector(orgUpX, orgUpY, orgUpZ)
        oCam.Perspective = orgPersp
        If orgPersp Then
            Try : oCam.PerspectiveAngle = orgPerspAng : Catch : End Try
        End If
        oCam.Apply()
        oView.Update()
        Try : Dim sh As Object = CreateObject("WScript.Shell") : sh.Run("powershell.exe -ExecutionPolicy Bypass -WindowStyle Hidden -File d:\WT3D_Project\Z_Tools\Auto_Stitch_Master.ps1", 0, True) : Catch : End Try

        Dim _baseName As String = System.IO.Path.GetFileNameWithoutExtension(oDoc.FullFileName)
        Dim _videoDir As String = "d:\WT3D_Project\2_Video_Renders"
        If Not isBatch Then
            Try : Process.Start("explorer.exe", _videoDir) : Catch : End Try
            Try : Process.Start("explorer.exe", saveFolder) : Catch : End Try
            ThisApplication.StatusBarText = "✅ CAM 1 HOÀN TẤT! Folder Video & Frames đã mở sẵn."
        End If
        ' -------------------------
    End Sub
End Class
