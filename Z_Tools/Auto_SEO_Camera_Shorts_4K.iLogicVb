AddReference "PresentationCore"
AddReference "WindowsBase"
AddReference "System.Drawing"
AddReference "System.Private.Windows.GdiPlus"
AddReference "System.Windows.Forms"
AddReference "System.Private.Windows.Core"

Imports System
Imports System.IO
Imports System.Windows.Forms
Imports System.Windows.Input
Imports System.Drawing
Imports Inventor

' ==============================================================================
' Auto_SEO_Camera_Shorts_4K.iLogicVb
' CHỤP ẢNH BỘ STUDIO METADATA 4K SHORTS (9:16 PORTRAIT ULTRA-HD 2160x3840)
' GÓC NGHỆ THUẬT: CĂN CHUẨN GÓC 3/4 ISOMETRIC / PERSPECTIVE TO FIT MÀN HÌNH 9:16
' Xuất toàn bộ bộ 15 ảnh chất lượng cực nét cho YouTube Shorts / TikTok / Reels / CGTrader / Fab
' ==============================================================================

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Try
            Dim oDoc As Inventor.Document = ThisDoc.Document
            Dim oView As Inventor.View = ThisApplication.ActiveView
            Dim oCam As Inventor.Camera = oView.Camera
            Dim originalDisplayMode As DisplayModeEnum = oView.DisplayMode

            Dim docPath As String = oDoc.FullFileName
            Dim docDir As String = System.IO.Path.GetDirectoryName(docPath)
            Dim baseName As String = System.IO.Path.GetFileNameWithoutExtension(docPath)
            Dim masterDir As String = "d:\WT3D_Project"

            ' Định vị thư mục gốc dự án chuẩn WT3D (Chứa 06_Renders_and_Media)
            Dim projectDir As String = docDir
            Dim curDir As String = docDir
            Dim foundMedia As Boolean = False
            Dim pParent As System.IO.DirectoryInfo = Nothing
            For scanDepth As Integer = 1 To 3
                If System.IO.Directory.Exists(System.IO.Path.Combine(curDir, "06_Renders_and_Media")) Then
                    projectDir = curDir
                    foundMedia = True
                    Exit For
                End If
                pParent = System.IO.Directory.GetParent(curDir)
                If pParent Is Nothing Then Exit For
                curDir = pParent.FullName
            Next
            If Not foundMedia Then
                For Each subFolder As String In New String() {"\01_assemblies", "\02_parts", "\03_drawings_2d"}
                    If docDir.ToLower().EndsWith(subFolder) Then
                        pParent = System.IO.Directory.GetParent(docDir)
                        If pParent IsNot Nothing Then projectDir = pParent.FullName
                        Exit For
                    End If
                Next
            End If

            Dim modelMediaDir As String = System.IO.Path.Combine(projectDir, "06_Renders_and_Media\04_Watermarked_Exports")
            If Not System.IO.Directory.Exists(modelMediaDir) Then
                Try : System.IO.Directory.CreateDirectory(modelMediaDir) : Catch : End Try
            End If

            ' Thư mục lưu ảnh Shorts 9:16 4K
            Dim savePath As String = masterDir + "\Preview_Image_Shorts\" + baseName
            If Not System.IO.Directory.Exists(savePath) Then System.IO.Directory.CreateDirectory(savePath)

            Dim exportsPath As String = masterDir + "\1_Exports_Batch\" + baseName
            If Not System.IO.Directory.Exists(exportsPath) Then System.IO.Directory.CreateDirectory(exportsPath)

            ' =======================================================
            ' TINH TOAN KICH THUOC BAO LOI (BOUNDING BOX)
            ' =======================================================
            Dim rBox As Box = Nothing
            If oDoc.DocumentType = DocumentTypeEnum.kAssemblyDocumentObject Then
                Dim asm As AssemblyDocument = CType(oDoc, AssemblyDocument)
                rBox = asm.ComponentDefinition.RangeBox
            End If

            ' --- 1. SET ÁNH SÁNG, PHÔNG NỀN & DỌN DẸP RÁC HIỂN THỊ ---
            Try
                oDoc.ObjectVisibility.AllWorkFeatures = False
                oDoc.ObjectVisibility.Sketches = False
                oDoc.ObjectVisibility.Sketches3D = False
                oDoc.ObjectVisibility.WeldmentSymbols = False
                oDoc.ObjectVisibility.ConstructionSurfaces = False
            Catch : End Try

            oView.DisplayMode = DisplayModeEnum.kShadedWithEdgesRendering
            oView.Update()

            oView.ShowAmbientShadows = True
            oView.ShowObjectShadows = True
            oView.ShowGroundShadows = True
            oView.ShowGroundReflections = False

            Try
                oDoc.ActiveLightingStyle = oDoc.LightingStyles.Item("Photo Booth")
            Catch
                Try : oDoc.ActiveLightingStyle = oDoc.LightingStyles.Item("Empty Lab") : Catch : End Try
            End Try

            ThisApplication.ColorSchemes.BackgroundType = BackgroundTypeEnum.kGradientBackgroundType

            ' ĐỘ PHÂN GIẢI 4K SHORTS (9:16 PORTRAIT ULTRA-HD: 2160 wide x 3840 high)
            Dim resWidth As Integer = 2160
            Dim resHeight As Integer = 3840
            Dim camW As Double
            Dim camH As Double

            Dim tg As TransientGeometry = ThisApplication.TransientGeometry

            ' =======================================================
            ' CHỤP ẢNH 0: GÓC MÁY ĐẤT NHÌN LÊN (LOW ANGLE HERO 9:16)
            ' =======================================================
            Try
                If rBox IsNot Nothing Then
                    Dim cx As Double = (rBox.MinPoint.X + rBox.MaxPoint.X) / 2.0
                    Dim cy As Double = (rBox.MinPoint.Y + rBox.MaxPoint.Y) / 2.0
                    Dim cz As Double = (rBox.MinPoint.Z + rBox.MaxPoint.Z) / 2.0
                    Dim mH As Double = rBox.MaxPoint.Y - rBox.MinPoint.Y
                    Dim mW As Double = Math.Max(rBox.MaxPoint.X - rBox.MinPoint.X, rBox.MaxPoint.Z - rBox.MinPoint.Z)

                    Dim eyePt As Inventor.Point = tg.CreatePoint(cx + mW * 0.85, rBox.MinPoint.Y - mH * 0.08, cz + mW * 1.05)
                    Dim targetPt As Inventor.Point = tg.CreatePoint(cx, rBox.MaxPoint.Y * 0.82, cz)
                    Dim upVec As Inventor.UnitVector = tg.CreateUnitVector(0, 1, 0)

                    oCam.Perspective = True
                    oCam.Eye = eyePt
                    oCam.Target = targetPt
                    oCam.UpVector = upVec
                    oCam.GetExtents(camW, camH)
                    oCam.SetExtents(camW * 0.70, camH * 0.70)
                    oCam.Apply()
                    oCam.SaveAsBitmap(savePath & "\" & baseName & "_00_LowAngle_Hero_916.png", resWidth, resHeight)
                Else
                    oCam.Perspective = True
                    oCam.ViewOrientationType = ViewOrientationTypeEnum.kIsoTopRightViewOrientation
                    oCam.Fit()
                    oCam.GetExtents(camW, camH)
                    oCam.SetExtents(camW * 0.65, camH * 0.65)
                    oCam.Apply()
                    oCam.SaveAsBitmap(savePath & "\" & baseName & "_00_LowAngle_Hero_916.png", resWidth, resHeight)
                End If
            Catch : End Try
            If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 1: GÓC 3/4 TRONG PHỐI CẢNH (HERO 3/4 OVERALL 9:16)
            ' =======================================================
            oCam.Perspective = True
            oCam.ViewOrientationType = ViewOrientationTypeEnum.kIsoTopRightViewOrientation
            oCam.Fit()
            oCam.GetExtents(camW, camH)
            oCam.SetExtents(camW * 0.65, camH * 0.65) ' Ép zoom vừa khít 90% màn hình 9:16
            oCam.Apply()
            oCam.SaveAsBitmap(savePath & "\" & baseName & "_01_Overall_Hero_916.png", resWidth, resHeight)
            If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 2: GÓC 3/4 TRÁI (ISO TOP LEFT 9:16)
            ' =======================================================
            oCam.Perspective = True
            oCam.ViewOrientationType = ViewOrientationTypeEnum.kIsoTopLeftViewOrientation
            oCam.Fit()
            oCam.GetExtents(camW, camH)
            oCam.SetExtents(camW * 0.65, camH * 0.65)
            oCam.Apply()
            oCam.SaveAsBitmap(savePath & "\" & baseName & "_02_Piping_Routing_916.png", resWidth, resHeight)
            If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 3: GÓC 3/4 TRÊN TOP LAYOUT (TOP 3/4 PERSPECTIVE 9:16)
            ' =======================================================
            oCam.Perspective = True
            oCam.ViewOrientationType = ViewOrientationTypeEnum.kIsoTopRightViewOrientation
            oCam.Fit()
            oCam.GetExtents(camW, camH)
            oCam.SetExtents(camW * 0.75, camH * 0.75)
            oCam.Apply()
            oCam.SaveAsBitmap(savePath & "\" & baseName & "_03_Top_Plan_Layout_916.png", resWidth, resHeight)
            If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 4A, 4B, 4C: WIREFRAME 9:16
            ' =======================================================
            oView.DisplayMode = DisplayModeEnum.kWireframeRendering
            oView.Update()

            ' WIREFRAME 3/4 PHẢI
            oCam.Perspective = True
            oCam.ViewOrientationType = ViewOrientationTypeEnum.kIsoTopRightViewOrientation
            oCam.Fit()
            oCam.GetExtents(camW, camH)
            oCam.SetExtents(camW * 0.65, camH * 0.65)
            oCam.Apply()
            oCam.SaveAsBitmap(savePath & "\" & baseName & "_04a_CAD_Wireframe_Proof_916.png", resWidth, resHeight)
            If CheckEscape() Then
                    ThisApplication.StatusBarText = "🛑 ĐÃ DỪNG TIẾN TRÌNH THEO LỆNH (GIỮ PHÍM ESC)!"
                    Exit Sub
                End If
                SafeYield(20)

            ' WIREFRAME FRONT 3/4
            oCam.Perspective = True
            oCam.ViewOrientationType = ViewOrientationTypeEnum.kFrontViewOrientation
            oCam.Fit()
            oCam.GetExtents(camW, camH)
            oCam.SetExtents(camW * 0.85, camH * 0.85)
            oCam.Apply()
            oCam.SaveAsBitmap(savePath & "\" & baseName & "_04b_CAD_Wireframe_Front_916.png", resWidth, resHeight)
            If CheckEscape() Then
                    ThisApplication.StatusBarText = "🛑 ĐÃ DỪNG TIẾN TRÌNH THEO LỆNH (GIỮ PHÍM ESC)!"
                    Exit Sub
                End If
                SafeYield(20)

            ' WIREFRAME DETAIL CLOSE-UP 3/4
            oCam.Perspective = True
            oCam.ViewOrientationType = ViewOrientationTypeEnum.kIsoTopLeftViewOrientation
            oCam.Fit()
            oCam.GetExtents(camW, camH)
            oCam.SetExtents(camW * 0.45, camH * 0.45)
            oCam.Apply()
            oCam.SaveAsBitmap(savePath & "\" & baseName & "_04c_CAD_Wireframe_Detail_916.png", resWidth, resHeight)
            If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 04D & 04E: VISIBLE EDGE 3/4 9:16
            ' =======================================================
            oView.DisplayMode = DisplayModeEnum.kWireframeNoHiddenEdges
            oView.Update()

            oCam.Perspective = True
            oCam.ViewOrientationType = ViewOrientationTypeEnum.kIsoTopRightViewOrientation
            oCam.Fit()
            oCam.GetExtents(camW, camH)
            oCam.SetExtents(camW * 0.68, camH * 0.68)
            oCam.Apply()
            oCam.SaveAsBitmap(savePath & "\" & baseName & "_04d_VisibleEdge_3Q_Right_916.png", resWidth, resHeight)
            If CheckEscape() Then
                    ThisApplication.StatusBarText = "🛑 ĐÃ DỪNG TIẾN TRÌNH THEO LỆNH (GIỮ PHÍM ESC)!"
                    Exit Sub
                End If
                SafeYield(20)

            oCam.Perspective = True
            oCam.ViewOrientationType = ViewOrientationTypeEnum.kIsoTopLeftViewOrientation
            oCam.Fit()
            oCam.GetExtents(camW, camH)
            oCam.SetExtents(camW * 0.68, camH * 0.68)
            oCam.Apply()
            oCam.SaveAsBitmap(savePath & "\" & baseName & "_04e_VisibleEdge_3Q_Left_916.png", resWidth, resHeight)
            If CheckEscape() Then
                    ThisApplication.StatusBarText = "🛑 ĐÃ DỪNG TIẾN TRÌNH THEO LỆNH (GIỮ PHÍM ESC)!"
                    Exit Sub
                End If
                SafeYield(20)

            ' TRẢ VỀ SHADED WITH EDGES
            oView.DisplayMode = DisplayModeEnum.kShadedWithEdgesRendering
            oView.Update()

            ' =======================================================
            ' CHỤP ẢNH 5, 6, 7: CÁC MẶT CHIẾU BẮT MẮT 9:16
            ' =======================================================
            oCam.Perspective = True

            oCam.ViewOrientationType = ViewOrientationTypeEnum.kFrontViewOrientation
            oCam.Fit()
            oCam.GetExtents(camW, camH)
            oCam.SetExtents(camW * 0.85, camH * 0.85)
            oCam.Apply()
            oCam.SaveAsBitmap(savePath & "\" & baseName & "_05_Front_Elevation_916.png", resWidth, resHeight)
            If CheckEscape() Then
                    ThisApplication.StatusBarText = "🛑 ĐÃ DỪNG TIẾN TRÌNH THEO LỆNH (GIỮ PHÍM ESC)!"
                    Exit Sub
                End If
                SafeYield(20)

            oCam.ViewOrientationType = ViewOrientationTypeEnum.kRightViewOrientation
            oCam.Fit()
            oCam.GetExtents(camW, camH)
            oCam.SetExtents(camW * 0.85, camH * 0.85)
            oCam.Apply()
            oCam.SaveAsBitmap(savePath & "\" & baseName & "_06_Right_Profile_916.png", resWidth, resHeight)
            If CheckEscape() Then
                    ThisApplication.StatusBarText = "🛑 ĐÃ DỪNG TIẾN TRÌNH THEO LỆNH (GIỮ PHÍM ESC)!"
                    Exit Sub
                End If
                SafeYield(20)

            oCam.ViewOrientationType = ViewOrientationTypeEnum.kLeftViewOrientation
            oCam.Fit()
            oCam.GetExtents(camW, camH)
            oCam.SetExtents(camW * 0.85, camH * 0.85)
            oCam.Apply()
            oCam.SaveAsBitmap(savePath & "\" & baseName & "_07_Left_Profile_916.png", resWidth, resHeight)
            If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 8, 9: DETAIL CLOSE-UPS 9:16
            ' =======================================================
            oCam.Perspective = True

            oCam.ViewOrientationType = ViewOrientationTypeEnum.kIsoTopRightViewOrientation
            oCam.Fit()
            oCam.GetExtents(camW, camH)
            oCam.SetExtents(camW * 0.48, camH * 0.48)
            oCam.Apply()
            oCam.SaveAsBitmap(savePath & "\" & baseName & "_08_Detail_CloseUp_1_916.png", resWidth, resHeight)
            If CheckEscape() Then
                    ThisApplication.StatusBarText = "🛑 ĐÃ DỪNG TIẾN TRÌNH THEO LỆNH (GIỮ PHÍM ESC)!"
                    Exit Sub
                End If
                SafeYield(20)

            oCam.ViewOrientationType = ViewOrientationTypeEnum.kIsoTopLeftViewOrientation
            oCam.Fit()
            oCam.GetExtents(camW, camH)
            oCam.SetExtents(camW * 0.45, camH * 0.45)
            oCam.Apply()
            oCam.SaveAsBitmap(savePath & "\" & baseName & "_09_Detail_CloseUp_2_916.png", resWidth, resHeight)
            If CheckEscape() Then
                    ThisApplication.StatusBarText = "🛑 ĐÃ DỪNG TIẾN TRÌNH THEO LỆNH (GIỮ PHÍM ESC)!"
                    Exit Sub
                End If
                SafeYield(20)

            ' =======================================================
            ' CHỤP ẢNH 10, 11, 12: BỘ ẢNH 3/4 MICRO CLOSE-UP 9:16 (CẬN CẢNH SIÊU NÉT PHỐI CẢNH 3/4)
            ' =======================================================
            ' 10. MICRO 3/4 PHẢI (VALVE HEADER 9:16)
            oCam.Perspective = True
            oCam.ViewOrientationType = ViewOrientationTypeEnum.kIsoTopRightViewOrientation
            oCam.Fit()
            oCam.GetExtents(camW, camH)
            oCam.SetExtents(camW * 0.35, camH * 0.35)
            oCam.Apply()
            oCam.SaveAsBitmap(savePath & "\" & baseName & "_10_Micro_3Q_Valve_Header_916.png", resWidth, resHeight)
            If CheckEscape() Then
                    ThisApplication.StatusBarText = "🛑 ĐÃ DỪNG TIẾN TRÌNH THEO LỆNH (GIỮ PHÍM ESC)!"
                    Exit Sub
                End If
                SafeYield(20)

            ' 11. MICRO 3/4 TRÁI (PUMP MANIFOLD 9:16)
            oCam.Perspective = True
            oCam.ViewOrientationType = ViewOrientationTypeEnum.kIsoTopLeftViewOrientation
            oCam.Fit()
            oCam.GetExtents(camW, camH)
            oCam.SetExtents(camW * 0.35, camH * 0.35)
            oCam.Apply()
            oCam.SaveAsBitmap(savePath & "\" & baseName & "_11_Micro_3Q_Pump_Manifold_916.png", resWidth, resHeight)
            If CheckEscape() Then
                    ThisApplication.StatusBarText = "🛑 ĐÃ DỪNG TIẾN TRÌNH THEO LỆNH (GIỮ PHÍM ESC)!"
                    Exit Sub
                End If
                SafeYield(20)

            ' 12. MICRO 3/4 WIREFRAME TECHNICAL (VISIBLE EDGE 9:16)
            oView.DisplayMode = DisplayModeEnum.kWireframeNoHiddenEdges
            oView.Update()
            oCam.Perspective = True
            oCam.ViewOrientationType = ViewOrientationTypeEnum.kIsoTopRightViewOrientation
            oCam.Fit()
            oCam.GetExtents(camW, camH)
            oCam.SetExtents(camW * 0.35, camH * 0.35)
            oCam.Apply()
            oCam.SaveAsBitmap(savePath & "\" & baseName & "_12_Micro_3Q_Wireframe_Detail_916.png", resWidth, resHeight)
            If CheckEscape() Then
                    ThisApplication.StatusBarText = "🛑 ĐÃ DỪNG TIẾN TRÌNH THEO LỆNH (GIỮ PHÍM ESC)!"
                    Exit Sub
                End If
                SafeYield(20)

            oView.DisplayMode = DisplayModeEnum.kShadedWithEdgesRendering
            oView.Update()

            ' =======================================================
            ' BURN WATERMARK DIMENSIONS & COPYRIGHT OVERLAY TỔNG LỰC (SHORTS 4K 9:16)
            ' =======================================================
            Try
                Dim pngFiles As String() = System.IO.Directory.GetFiles(savePath, "*.png")
                For Each imgFile As String In pngFiles
                    If CheckEscape() Then
                        ThisApplication.StatusBarText = "🛑 ĐÃ DỪNG VÒNG LẶP THEO LỆNH (GIỮ PHÍM ESC)!"
                        Exit Sub
                    End If
                    SafeYield(10)
                    If imgFile.Contains("temp_") Then Continue For
                    If imgFile.Contains("_GA_") OrElse imgFile.Contains("_Drawing_") Then Continue For

                    Dim tempImgPath As String = savePath & "\temp_" & System.IO.Path.GetFileName(imgFile)
                    Dim isHero As Boolean = imgFile.Contains("_01_Overall_Hero") OrElse imgFile.Contains("_00_LowAngle_Hero")

                    Using bmp As New System.Drawing.Bitmap(imgFile)
                        Using g As System.Drawing.Graphics = System.Drawing.Graphics.FromImage(bmp)
                            g.SmoothingMode = System.Drawing.Drawing2D.SmoothingMode.HighQuality
                            g.InterpolationMode = System.Drawing.Drawing2D.InterpolationMode.HighQualityBicubic
                            g.PixelOffsetMode = System.Drawing.Drawing2D.PixelOffsetMode.HighQuality
                            g.TextRenderingHint = System.Drawing.Text.TextRenderingHint.AntiAliasGridFit

                            ' ------------------------------------------------------------------
                            ' LỚP 1: LÁ CỜ VIỆT NAM (GÓC TRÊN BÊN TRÁI 9:16)
                            ' ------------------------------------------------------------------
                            Dim isVertical As Boolean = (bmp.Height > bmp.Width)
                            Dim flagW As Single = bmp.Width * (If(isVertical, 0.140F, 0.105F))
                            Dim flagH As Single = flagW * 0.6667F
                            Dim flagX As Single = bmp.Width * (If(isVertical, 0.045F, 0.030F))
                            Dim flagY As Single = bmp.Height * 0.030F
                            Dim flagPath As String = masterDir & "\Z_Tools\vietnam_flag.png"
                            If System.IO.File.Exists(flagPath) Then
                                Try
                                    Dim flagBytes As Byte() = System.IO.File.ReadAllBytes(flagPath)
                                    Using flagMs As New System.IO.MemoryStream(flagBytes)
                                        Using flagImg As New System.Drawing.Bitmap(flagMs)
                                            g.DrawImage(flagImg, flagX, flagY, flagW, flagH)
                                        End Using
                                    End Using
                                Catch : End Try
                            End If

                            ' ------------------------------------------------------------------
                            ' LỚP 2: BẢN QUYỀN THỦY TINH CHÍNH GIỮA MÀN HÌNH (@tanphan1105)
                            ' ------------------------------------------------------------------
                            Dim mailY As Single = bmp.Height * (If(isVertical, 0.43F, 0.44F))
                            g.TranslateTransform(bmp.Width / 2.0F, mailY)
                            Dim mailText As String = "@tanphan1105"
                            Dim mailSize As Single = bmp.Width * (If(isVertical, 0.082F, 0.052F))
                            Using mailFont As New System.Drawing.Font("Arial Black", mailSize, System.Drawing.FontStyle.Bold)
                                Using gp2 As New System.Drawing.Drawing2D.GraphicsPath()
                                    Dim sf2 As New System.Drawing.StringFormat() 
                                    sf2.Alignment = System.Drawing.StringAlignment.Center
                                    sf2.LineAlignment = System.Drawing.StringAlignment.Center
                                    gp2.AddString(mailText, mailFont.FontFamily, CInt(mailFont.Style), mailFont.Size, New System.Drawing.PointF(0, 0), sf2)
                                    Dim pThick2 As Single = Math.Max(1.0F, bmp.Width * 0.0015F)
                                    Using darkPen2 As New System.Drawing.Pen(System.Drawing.Color.FromArgb(35, 0, 0, 0), pThick2)
                                        g.TranslateTransform(pThick2, pThick2)
                                        g.DrawPath(darkPen2, gp2)
                                        g.TranslateTransform(-pThick2, -pThick2)
                                    End Using
                                    Using glassBrush As New System.Drawing.SolidBrush(System.Drawing.Color.FromArgb(10, 255, 255, 255))
                                        g.FillPath(glassBrush, gp2)
                                    End Using
                                    Using lightPen2 As New System.Drawing.Pen(System.Drawing.Color.FromArgb(55, 255, 255, 255), pThick2)
                                        g.TranslateTransform(-pThick2, -pThick2)
                                        g.DrawPath(lightPen2, gp2)
                                        g.TranslateTransform(pThick2, pThick2)
                                    End Using
                                End Using
                            End Using
                            g.ResetTransform()

                            ' ------------------------------------------------------------------
                            ' LỚP 3: THẺ GREEN CARD LOGO DIAGONAL GRADIENT (CĂN GIỮA DƯỚI CÙNG 90% CHIỀU RỘNG)
                            ' ------------------------------------------------------------------
                            Dim brandText As String = "WaterTreatment3D"
                            Dim contactText As String = "@tanphan1105 | Zalo: +84985267326"
                            Dim brandSize As Single = bmp.Width * (If(isVertical, 0.022F, 0.013F))
                            Dim contactSize As Single = bmp.Width * (If(isVertical, 0.026F, 0.015F))

                            Using brandFont As New System.Drawing.Font("Arial", brandSize, System.Drawing.FontStyle.Bold)
                            Using contactFont As New System.Drawing.Font("Arial", contactSize, System.Drawing.FontStyle.Bold)
                                Dim brandSz As System.Drawing.SizeF = g.MeasureString(brandText, brandFont)
                                Dim contactSz As System.Drawing.SizeF = g.MeasureString(contactText, contactFont)
                                Dim maxW As Single = Math.Max(brandSz.Width, contactSz.Width)
                                Dim qrSize As Single = bmp.Width * (If(isVertical, 0.145F, 0.075F))
                                Dim cPad As Single = bmp.Width * (If(isVertical, 0.022F, 0.010F))
                                Dim gap As Single = bmp.Width * (If(isVertical, 0.022F, 0.014F))

                                ' LOAD QR CODE SAFE VIA MEMORYSTREAM
                                Dim hasQR As Boolean = False
                                Dim qrPath As String = masterDir & "\Z_Tools\wt3d_qr_green.png"
                                Dim qrBmp As System.Drawing.Bitmap = Nothing
                                If System.IO.File.Exists(qrPath) Then
                                    Try
                                        Dim qrBytes As Byte() = System.IO.File.ReadAllBytes(qrPath)
                                        Dim qrMs As New System.IO.MemoryStream(qrBytes)
                                        qrBmp = New System.Drawing.Bitmap(qrMs)
                                        hasQR = True
                                    Catch : End Try
                                End If

                                Dim effQRSize As Single = If(hasQR, qrSize, 0.0F)
                                Dim effGap As Single = If(hasQR, gap, 0.0F)

                                Dim totalW As Single = maxW + effGap + effQRSize
                                Dim textBlockH As Single = brandSz.Height + contactSz.Height + (bmp.Height * If(isVertical, 0.012F, 0.008F))
                                Dim totalH As Single = Math.Max(textBlockH, qrSize)

                                Dim cardX As Single
                                Dim cardY As Single
                                If isVertical Then
                                    cardX = (bmp.Width - (totalW + cPad*2)) / 2.0F
                                    cardY = bmp.Height - totalH - (bmp.Height * 0.035F) - cPad*2
                                Else
                                    cardX = bmp.Width - totalW - (bmp.Width * 0.025F) - cPad*2
                                    cardY = bmp.Height - totalH - (bmp.Height * 0.035F) - cPad*2
                                End If

                                ' DRAW ROUNDED RECTANGLE GRADIENT CARD
                                Dim rectW As Single = totalW + cPad*2
                                Dim rectH As Single = totalH + cPad*2
                                Dim rRadius As Single = Math.Max(6.0F, bmp.Width * 0.008F)
                                Using cardPath As New System.Drawing.Drawing2D.GraphicsPath()
                                    cardPath.AddArc(cardX, cardY, rRadius, rRadius, 180, 90)
                                    cardPath.AddArc(cardX + rectW - rRadius, cardY, rRadius, rRadius, 270, 90)
                                    cardPath.AddArc(cardX + rectW - rRadius, cardY + rectH - rRadius, rRadius, rRadius, 0, 90)
                                    cardPath.AddArc(cardX, cardY + rectH - rRadius, rRadius, rRadius, 90, 90)
                                    cardPath.CloseAllFigures()

                                    Dim rectF As New System.Drawing.RectangleF(cardX, cardY, rectW, rectH)
                                    Dim col1 As System.Drawing.Color = System.Drawing.Color.FromArgb(225, 52, 199, 89)
                                    Dim col2 As System.Drawing.Color = System.Drawing.Color.FromArgb(220, 24, 150, 68)
                                    Using gradBrush As New System.Drawing.Drawing2D.LinearGradientBrush(rectF, col1, col2, 45.0F)
                                        g.FillPath(gradBrush, cardPath)
                                    End Using
                                    Using borderPen As New System.Drawing.Pen(System.Drawing.Color.FromArgb(240, 255, 255, 255), 1.0F)
                                        g.DrawPath(borderPen, cardPath)
                                    End Using
                                End Using

                                Dim currY As Single = cardY + cPad + (totalH - textBlockH) / 2.0F

                                ' DRAW BRAND TEXT & SHADOW
                                Using shadowBrush As New System.Drawing.SolidBrush(System.Drawing.Color.FromArgb(110, 10, 40, 15))
                                    g.DrawString(brandText, brandFont, shadowBrush, cardX + cPad + 3, currY + 3)
                                End Using
                                Using mainBrush As New System.Drawing.SolidBrush(System.Drawing.Color.FromArgb(255, 255, 255, 255))
                                    g.DrawString(brandText, brandFont, mainBrush, cardX + cPad, currY)
                                End Using

                                currY += brandSz.Height + (bmp.Height * 0.004F)

                                ' DRAW CONTACT TEXT & SHADOW
                                Using shadowBrush As New System.Drawing.SolidBrush(System.Drawing.Color.FromArgb(110, 10, 40, 15))
                                    g.DrawString(contactText, contactFont, shadowBrush, cardX + cPad + 3, currY + 3)
                                End Using
                                Using mainBrush As New System.Drawing.SolidBrush(System.Drawing.Color.FromArgb(255, 255, 255, 255))
                                    g.DrawString(contactText, contactFont, mainBrush, cardX + cPad, currY)
                                End Using

                                If hasQR AndAlso qrBmp IsNot Nothing Then
                                    Try
                                        Dim qrX As Single = cardX + cPad + maxW + gap
                                        Dim qrY As Single = cardY + cPad + (totalH - qrSize)/2.0F
                                        Using qrBgPen As New System.Drawing.SolidBrush(System.Drawing.Color.FromArgb(255, 255, 255, 255))
                                            g.FillRectangle(qrBgPen, qrX - 4, qrY - 4, qrSize + 8, qrSize + 8)
                                        End Using
                                        g.DrawImage(qrBmp, qrX, qrY, qrSize, qrSize)
                                        qrBmp.Dispose()
                                    Catch : End Try
                                End If
                            End Using
                            End Using
                        End Using
                        bmp.Save(tempImgPath, System.Drawing.Imaging.ImageFormat.Png)
                    End Using

                    System.IO.File.Delete(imgFile)
                    System.IO.File.Move(tempImgPath, imgFile)
                Next
            Catch ex As Exception
            End Try

            For Each f As String In System.IO.Directory.GetFiles(savePath, "*_916.png")
                    If CheckEscape() Then
                        ThisApplication.StatusBarText = "🛑 ĐÃ DỪNG VÒNG LẶP THEO LỆNH (GIỮ PHÍM ESC)!"
                        Exit Sub
                    End If
                    SafeYield(10)
                Try
                    System.IO.File.Copy(f, exportsPath & "\" & System.IO.Path.GetFileName(f), True)
                    System.IO.File.Copy(f, System.IO.Path.Combine(modelMediaDir, System.IO.Path.GetFileName(f)), True)
                Catch : End Try
            Next

            Try : System.Diagnostics.Process.Start("explorer.exe", savePath) : Catch : End Try

            ThisApplication.StatusBarText = "✅ Auto SEO Camera Shorts 4K (9:16) chụp xong trọn bộ 15 ảnh (Đã lưu vào 06_Renders_and_Media và Preview_Image_Shorts)!"

        Catch ex As Exception
            MessageBox.Show("Lỗi Auto SEO Camera Shorts 4K: " & ex.Message, "Báo Động 9:16")
        End Try
    End Sub
End Class
