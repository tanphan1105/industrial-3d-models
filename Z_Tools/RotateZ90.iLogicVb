' iLogic Rule: Rotate selected component by 90 degrees around Assembly's Global Z-Axis

AddReference "System.Windows.Forms"
AddReference "System.Private.Windows.Core"

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

        Public Sub Main()
            Dim doc As AssemblyDocument = ThisApplication.ActiveDocument
            Dim def As AssemblyComponentDefinition = doc.ComponentDefinition

            If doc.SelectSet.Count = 0 Then Exit Sub
            Dim occ As ComponentOccurrence = TryCast(doc.SelectSet(1), ComponentOccurrence)
            If occ Is Nothing Then Exit Sub

            ' Clean name to avoid special character errors in Inventor constraint naming
            Dim cleanOccName As String = occ.Name.Replace(":", "_").Replace(" ", "_").Replace(".", "_")

            Dim targetConstraintName As String = "OM_ROT_Z_" & cleanOccName
            Dim otherConstraintNameX As String = "OM_ROT_X_" & cleanOccName
            Dim otherConstraintNameY As String = "OM_ROT_Y_" & cleanOccName

            ' 1. Delete conflicting rotation constraints on other axes first to avoid warnings
            For Each constraint As AssemblyConstraint In def.Constraints
                If constraint.Name = otherConstraintNameX Or constraint.Name = otherConstraintNameY Then
                    Try
                        constraint.Delete()
                    Catch
                        ' Ignore if unable to delete
                    End Try
                End If
            Next

            ' 2. Find or create the Z rotation constraint
            Dim angleConst As AngleConstraint = Nothing
            For Each constraint As AssemblyConstraint In def.Constraints
                If constraint.Name = targetConstraintName Then
                    angleConst = TryCast(constraint, AngleConstraint)
                    Exit For
                End If
            Next

            If angleConst IsNot Nothing Then
                Try
                    Dim currentAngleRad As Double = angleConst.Angle.Value
                    Dim currentAngleDeg As Double = currentAngleRad * (180.0 / Math.PI)
                    Dim newAngleDeg As Double = (Math.Round(currentAngleDeg) + 90) Mod 360
                    angleConst.Angle.Value = newAngleDeg * (Math.PI / 180.0)
                    doc.Update()
                Catch ex As Exception
                    ' Fail silently
                End Try
            Else
                Try
                    ' To rotate around Z-axis, the constrained planes must be parallel to Z-axis.
                    ' We must use XZ Plane (Plane 2) instead of XY Plane (Plane 3) because XY is perpendicular to Z.
                    Dim asmXZ As WorkPlane = def.WorkPlanes(2) ' Assembly XZ Plane (parallel to Z-axis)
                    Dim occXZ As WorkPlane = occ.Definition.WorkPlanes(2) ' Component XZ Plane
                    Dim occXZProxy As Object = Nothing
                    occ.CreateGeometryProxy(occXZ, occXZProxy)

                    Dim asmzAxis As WorkAxis = def.WorkAxes(3) ' Assembly Global Z Axis (Rotation Axis)

                    Dim newAngleConst As AngleConstraint = def.Constraints.AddAngleConstraint(
                        asmXZ, 
                        occXZProxy, 
                        90.0 * (Math.PI / 180.0), 
                        AngleConstraintSolutionTypeEnum.kReferenceVectorSolution,
                        asmzAxis
                    )

                    ' Set unique name (cleaned)
                    newAngleConst.Name = targetConstraintName
                    doc.Update()
                Catch ex As Exception
                    ' Fail silently
                End Try
            End If
            End Sub
End Class
