' ==============================================================================
' WT3D STUDIO RIG: B0_SET_DARK_CINEMATIC_STUDIO.iLogicVb
' TIÊU CHUẨN: MÔI TRƯỜNG & ÁNH SÁNG DARK CINEMATIC STUDIO (STARK BLACK / CYBERPUNK)
' TÍCH HỢP: DARK SKY CONTRAST + DRAMATIC RIM LIGHTING (125%) + GROUND WET REFLECTION
' CHUYÊN DÙNG: VIDEO SHORTS/TIKTOK, COVER 3D HI-TECH, THUMBNAIL FAB/SKETCHFAB ĐẲNG CẤP
' PHÙ HỢP CẢ PART (.IPT) VÀ ASSEMBLY (.IAM) - BẢO VỆ PHÍM ESC KHẨN CẤP
' ==============================================================================

AddReference "System.Windows.Forms"
AddReference "System.Private.Windows.Core"
AddReference "System.Drawing"

Imports System
Imports System.Drawing
Imports System.Runtime.InteropServices
Imports System.Windows.Forms
Imports Inventor

Public Class ThisRule
    <DllImport("user32.dll")>
    Private Shared Function GetAsyncKeyState(ByVal vKey As Integer) As Short
    End Function
    Private Const VK_ESCAPE As Integer = &H1B

    Private Function CheckEscape() As Boolean
        Try
            System.Windows.Forms.Application.DoEvents()
            If (GetAsyncKeyState(VK_ESCAPE) And &H8000) <> 0 OrElse GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Dim oApp As Inventor.Application = ThisApplication
        Dim oDoc As Document = oApp.ActiveDocument
        If oDoc Is Nothing Then
            MessageBox.Show("Vui long mo mot chi tiet (.ipt) hoac cum lap (.iam) trong Inventor!", "WT3D Dark Cinematic", MessageBoxButtons.OK, MessageBoxIcon.Warning)
            Exit Sub
        End If

        Dim isPartDoc As Boolean = (TypeOf oDoc Is PartDocument)
        Dim isAsmDoc As Boolean = (TypeOf oDoc Is AssemblyDocument)

        If Not isPartDoc AndAlso Not isAsmDoc Then
            MessageBox.Show("Tai lieu hien tai khong phai la Part (.ipt) hoac Assembly (.iam)!", "WT3D Dark Cinematic", MessageBoxButtons.OK, MessageBoxIcon.Warning)
            Exit Sub
        End If

        Dim tg As TransientGeometry = oApp.TransientGeometry
        Dim oView As Inventor.View = oApp.ActiveView
        If oView Is Nothing Then Exit Sub

        Try
            oApp.SilentOperation = True

            ' ==============================================================================
            ' 1. DỌN DẸP HIỂN THỊ TRIỆT ĐỂ (TẮT MẶT PHẲNG, TRỤC, GỐC TỌA ĐỘ, SKETCH)
            ' ==============================================================================
            Try
                Dim ctrlDef As ControlDefinition = oApp.CommandManager.ControlDefinitions.Item("AppAllWorkFeaturesCmd")
                If ctrlDef IsNot Nothing AndAlso ctrlDef.Pressed Then
                    ctrlDef.Execute()
                End If
            Catch : End Try

            Try
                oDoc.ObjectVisibility.AllWorkFeatures = False
                oDoc.ObjectVisibility.UserWorkPlanes = False
                oDoc.ObjectVisibility.OriginWorkPlanes = False
                oDoc.ObjectVisibility.UserWorkAxes = False
                oDoc.ObjectVisibility.OriginWorkAxes = False
                oDoc.ObjectVisibility.UserWorkPoints = False
                oDoc.ObjectVisibility.OriginWorkPoints = False
                oDoc.ObjectVisibility.OriginWorkFeatures = False
                oDoc.ObjectVisibility.Sketches = False
                oDoc.ObjectVisibility.Sketches3D = False
                oDoc.ObjectVisibility.WeldmentSymbols = False
                oDoc.ObjectVisibility.ConstructionSurfaces = False
            Catch : End Try

            ' ==============================================================================
            ' 2. KÍCH HOẠT LIGHTING STYLE TƯƠNG PHẢN ĐIỆN ẢNH (DARK SKY / TWO LIGHTS BACKUP)
            ' ==============================================================================
            Dim oStyles As LightingStyles = Nothing
            If isPartDoc Then
                oStyles = CType(oDoc, PartDocument).LightingStyles
            ElseIf isAsmDoc Then
                oStyles = CType(oDoc, AssemblyDocument).LightingStyles
            End If

            Dim targetLs As LightingStyle = Nothing

            If oStyles IsNot Nothing Then
                Try : targetLs = oStyles.Item("Dark Sky") : Catch : End Try

                If targetLs Is Nothing Then
                    Try : targetLs = oStyles.Item("KeyShot Studio") : Catch : End Try
                End If

                If targetLs Is Nothing Then
                    Try : targetLs = oStyles.Item("Two Lights") : Catch : End Try
                End If

                If targetLs Is Nothing Then
                    For Each ls As LightingStyle In oStyles
                        If CheckEscape() Then Exit Sub
                        SafeYield(5)
                        If ls.Name.ToLower().Contains("dark") OrElse ls.Name.ToLower().Contains("keyshot") OrElse ls.Name.ToLower().Contains("two") Then
                            targetLs = ls
                            Exit For
                        End If
                    Next
                End If

                If targetLs Is Nothing AndAlso oStyles.Count > 0 Then
                    targetLs = oStyles.Item(1)
                End If

                If targetLs IsNot Nothing Then
                    Try
                        If targetLs.StyleLocation = StyleLocationEnum.kLibraryStyleLocation Then
                            targetLs.ConvertToLocal()
                        End If
                    Catch : End Try

                    If isPartDoc Then
                        CType(oDoc, PartDocument).ActiveLightingStyle = targetLs
                    ElseIf isAsmDoc Then
                        CType(oDoc, AssemblyDocument).ActiveLightingStyle = targetLs
                    End If
                End If
            End If

            ' ==============================================================================
            ' 3. THIẾT LẬP HỆ THỐNG ÁNH SÁNG 4-LIGHT: DRAMATIC RIM RIG (TÁCH NỀN ĐEN SẮC LẸM)
            ' ==============================================================================
            Try
                Dim curStyle As LightingStyle = Nothing
                If isPartDoc Then
                    curStyle = CType(oDoc, PartDocument).ActiveLightingStyle
                ElseIf isAsmDoc Then
                    curStyle = CType(oDoc, AssemblyDocument).ActiveLightingStyle
                End If

                If curStyle IsNot Nothing Then
                    Try : curStyle.ShadowDirection = ShadowDirectionEnum.kAboveShadowDirection : Catch : End Try
                    Try : curStyle.ShadowDensity = 52.0 : Catch : End Try            ' Độ đậm bóng đổ sàn 52% (bóng mờ êm dịu chuẩn Anh Tấn)
                    Try : curStyle.ShadowSoftness = 50.0 : Catch : End Try           ' Độ mềm 50% (khuếch tán tự nhiên)
                    Try : curStyle.AmbientShadowIntensity = 18.0 : Catch : End Try   ' Ambient Shadows 18% (êm ái khe kẽ)

                    ' CẤU HÌNH 4 ĐÈN THEO VIEW SPACE (LUÔN BÁM THEO VIEWCUBE XOAY GÓC NÀO CŨNG NỔI KHỐI)
                    Dim lIdx As Integer = 1
                    For Each lt As Light In curStyle.Lights
                        If CheckEscape() Then Exit Sub
                        SafeYield(5)

                        If lIdx = 1 Then
                            ' Light 1: KEY LIGHT (Đèn chính - Trắng ấm sang trọng 4800K, rọi trực diện góc trên-trái)
                            Try : lt.On = True : Catch : End Try
                            Try : lt.LightType = LightTypeEnum.kViewSpaceLight : Catch : End Try
                            Try : lt.Color = oApp.TransientObjects.CreateColor(255, 250, 242) : Catch : End Try
                            Try : lt.Intensity = 0.95 : Catch : End Try
                            Try : lt.Direction = tg.CreateVector(0.320000, -0.320000, -0.892000) : Catch : End Try

                        ElseIf lIdx = 2 Then
                            ' Light 2: FILL LIGHT (Đèn phụ bù sáng - Xanh thép điện ảnh lạnh dịu 7000K, giữ bóng tương phản)
                            Try : lt.On = True : Catch : End Try
                            Try : lt.LightType = LightTypeEnum.kViewSpaceLight : Catch : End Try
                            Try : lt.Color = oApp.TransientObjects.CreateColor(215, 235, 255) : Catch : End Try
                            Try : lt.Intensity = 0.35 : Catch : End Try
                            Try : lt.Direction = tg.CreateVector(-0.350000, -0.150000, -0.924800) : Catch : End Try

                        ElseIf lIdx = 3 Then
                            ' Light 3: DRAMATIC RIM LIGHT (Đèn viền lưng cực mạnh 125% - Tạo viền sáng bạc sắc lẹm tách khỏi nền tối)
                            Try : lt.On = True : Catch : End Try
                            Try : lt.LightType = LightTypeEnum.kViewSpaceLight : Catch : End Try
                            Try : lt.Color = oApp.TransientObjects.CreateColor(255, 255, 255) : Catch : End Try
                            Try : lt.Intensity = 1.25 : Catch : End Try
                            Try : lt.Direction = tg.CreateVector(-0.480000, 0.480000, 0.733200) : Catch : End Try

                        ElseIf lIdx = 4 Then
                            ' Light 4: TOP ACCENT LIGHT (Đèn trần - Rọi sống lưng ống và nắp cột lọc từ trên xuống)
                            Try : lt.On = True : Catch : End Try
                            Try : lt.LightType = LightTypeEnum.kViewSpaceLight : Catch : End Try
                            Try : lt.Color = oApp.TransientObjects.CreateColor(245, 250, 255) : Catch : End Try
                            Try : lt.Intensity = 0.40 : Catch : End Try
                            Try : lt.Direction = tg.CreateVector(0.000000, -0.880000, -0.475000) : Catch : End Try
                        End If
                        lIdx += 1
                    Next
                End If
            Catch : End Try

                        ' ==============================================================================
            ' 4. THIẾT LẬP NỀN TỐI DARK THEME CHUẨN INVENTOR (MỊN MÀNG, NÉT ĐEN DỊU, KHÔNG VIỀN TRẮNG)
            ' ==============================================================================
            Try
                Dim appOpts As Inventor.ColorSchemes = oApp.ColorSchemes
                Dim setDark As Boolean = False
                
                ' Ưu tiên 1: ColorScheme "Dark" chính thức của Inventor (Nét xám đen dịu, không bị viền trắng thô)
                For Each cs As ColorScheme In appOpts
                    If CheckEscape() Then Exit Sub
                    If cs.Name.Equals("Dark", StringComparison.OrdinalIgnoreCase) Then
                        cs.Activate()
                        Try : cs.ReflectionEnvironmentFileName = "studio_02.dds" : Catch : End Try
                        setDark = True
                        Exit For
                    End If
                Next

                ' Ưu tiên 2: "Winter Night" hoặc "Deep Blue" nếu máy chưa có Dark
                If Not setDark Then
                    For Each cs As ColorScheme In appOpts
                        If cs.Name.Equals("Winter Night", StringComparison.OrdinalIgnoreCase) OrElse cs.Name.Equals("Deep Blue", StringComparison.OrdinalIgnoreCase) Then
                            cs.Activate()
                            Try : cs.ReflectionEnvironmentFileName = "studio_02.dds" : Catch : End Try
                            setDark = True
                            Exit For
                        End If
                    Next
                End If
            Catch : End Try

            Try
                oApp.ColorSchemes.BackgroundType = BackgroundTypeEnum.kGradientBackgroundType
            Catch : End Try

            ' ==============================================================================
            ' 5. CHẾ ĐỘ HIỂN THỊ, BÓNG ĐỔ SÂU & HIỆU ỨNG SÀN ƯỚT (WET FLOOR REFLECTION)
            ' ==============================================================================
            Try : oView.DisplayMode = DisplayModeEnum.kShadedWithEdgesRendering : Catch : End Try
            Try : oView.ShowGroundShadows = True : Catch : End Try
            Try : oView.ShowAmbientShadows = True : Catch : End Try       ' Ambient Occlusion (AO) sâu
            Try : oView.ShowObjectShadows = True : Catch : End Try        ' Bóng tương hỗ giữa các ống
            Try : oView.ShowGroundReflections = False : Catch : End Try     ' Phản xạ gương sàn triển lãm

            ' Góc nhìn phối cảnh 3D Perspective có tụ & Tự động căn vừa khung nhìn (Fit to View)
            Try
                Dim oCam As Camera = oView.Camera
                If Not oCam.Perspective Then
                    oCam.Perspective = True
                End If
                oCam.Fit()
                oCam.ApplyWithoutTransition()
            Catch : End Try

            ' Chất lượng hiển thị mượt mà khử răng cưa
            Try : oApp.DisplayOptions.DisplayQuality = DisplayQualityEnum.kSmootherDisplayQuality : Catch : End Try
            Try : oApp.DisplayOptions.AntiAliasing = True : Catch : End Try
            Try : oApp.DisplayOptions.SmoothLines = True : Catch : End Try

            ' ==============================================================================
            ' 6. TỰ ĐỘNG HIỆU CHỈNH ĐỘ BÓNG KIM LOẠI PBR CHO NỀN TỐI (TĂNG CƯỜNG PHẢN QUANG)
            ' ==============================================================================
            Dim docsToProcess As New System.Collections.Generic.List(Of Document)()
            docsToProcess.Add(oDoc)

            If isAsmDoc Then
                Try
                    For Each refDoc As Document In oDoc.AllReferencedDocuments
                        If TypeOf refDoc Is PartDocument Then
                            docsToProcess.Add(refDoc)
                        End If
                    Next
                Catch : End Try
            End If

            For Each targetDoc As Document In docsToProcess
                If CheckEscape() Then Exit Sub
                SafeYield(5)

                Try
                    Dim oAssets As Assets = targetDoc.Assets
                    For Each oAsset As Asset In oAssets
                        If CheckEscape() Then Exit Sub

                        Dim nm As String = ""
                        Try : nm = oAsset.DisplayName.ToLower() : Catch : Continue For : End Try

                        Dim gloss As Double = -1
                        Dim refl0 As Double = -1
                        Dim refl90 As Double = -1
                        Dim metallic As Double = -1

                        ' 1. Inox / Thép không gỉ / Chrome / Nickel (Bắt sáng viền rực rỡ trên nền tối)
                        If nm.Contains("inox") OrElse nm.Contains("stainless") OrElse nm.Contains("steel") OrElse nm.Contains("thép") OrElse nm.Contains("chrome") OrElse nm.Contains("nickel") Then
                            gloss    = 0.85    ' Rất mịn, bóng bẩy
                            refl0    = 0.65    ' Phản xạ trực diện
                            refl90   = 0.95    ' Viền sáng bạc lấp lánh (Fresnel 95%)
                            metallic = 1.00

                        ' 2. Nhôm / Aluminum Anodized
                        ElseIf nm.Contains("nhôm") OrElse nm.Contains("aluminum") OrElse nm.Contains("aluminium") OrElse nm.Contains("alum") Then
                            gloss    = 0.78
                            refl0    = 0.52
                            refl90   = 0.88
                            metallic = 1.00

                        ' 3. Đồng / Brass / Bronze / Copper
                        ElseIf nm.Contains("đồng") OrElse nm.Contains("brass") OrElse nm.Contains("bronze") OrElse nm.Contains("copper") Then
                            gloss    = 0.82
                            refl0    = 0.58
                            refl90   = 0.92
                            metallic = 1.00

                        ' 4. Composite / FRP / Cột lọc bồn FRP / Gelcoat
                        ElseIf nm.Contains("composite") OrElse nm.Contains("frp") OrElse nm.Contains("cột") OrElse nm.Contains("bồn") Then
                            gloss    = 0.72
                            refl0    = 0.25
                            refl90   = 0.80
                            metallic = 0.00

                        ' 5. Nhựa PVC / HDPE / uPVC / PPR / Ống nước
                        ElseIf nm.Contains("pvc") OrElse nm.Contains("hdpe") OrElse nm.Contains("upvc") OrElse nm.Contains("pp") OrElse nm.Contains("nhựa") OrElse nm.Contains("plastic") Then
                            gloss    = 0.52
                            refl0    = 0.10
                            refl90   = 0.55
                            metallic = 0.00

                        ' 6. Sơn tĩnh điện / Epoxy Paint / Powder Coat / Khung bệ sơn
                        ElseIf nm.Contains("sơn") OrElse nm.Contains("paint") OrElse nm.Contains("powder") OrElse nm.Contains("epoxy") OrElse nm.Contains("coat") Then
                            gloss    = 0.56
                            refl0    = 0.10
                            refl90   = 0.55
                            metallic = 0.00

                        ' 7. Thủy tinh / Kính / Glass / Lưu lượng kế / Đèn UV
                        ElseIf nm.Contains("thủy tinh") OrElse nm.Contains("glass") OrElse nm.Contains("acrylic") OrElse nm.Contains("kính") Then
                            gloss    = 0.98
                            refl0    = 0.10
                            refl90   = 0.98
                            metallic = 0.00

                        ' 8. Gang / Sắt đúc / Cast Iron / Thân bơm
                        ElseIf nm.Contains("gang") OrElse nm.Contains("iron") OrElse nm.Contains("cast") OrElse nm.Contains("carbon") OrElse nm.Contains("sắt") Then
                            gloss    = 0.45
                            refl0    = 0.22
                            refl90   = 0.55
                            metallic = 1.00

                        ' 9. Cao su / Rubber / EPDM Gasket
                        ElseIf nm.Contains("cao su") OrElse nm.Contains("rubber") OrElse nm.Contains("gasket") OrElse nm.Contains("oring") OrElse nm.Contains("epdm") OrElse nm.Contains("viton") Then
                            gloss    = 0.18
                            refl0    = 0.03
                            refl90   = 0.15
                            metallic = 0.00
                        End If

                        If gloss >= 0 Then
                            Try
                                Dim propG As AssetValue = oAsset("generic_glossiness")
                                If propG IsNot Nothing Then CType(propG, FloatAssetValue).Value = gloss
                            Catch : End Try
                            Try
                                Dim propR0 As AssetValue = oAsset("generic_reflectivity_at_0deg")
                                If propR0 IsNot Nothing Then CType(propR0, FloatAssetValue).Value = refl0
                            Catch : End Try
                            Try
                                Dim propR90 As AssetValue = oAsset("generic_reflectivity_at_90deg")
                                If propR90 IsNot Nothing Then CType(propR90, FloatAssetValue).Value = refl90
                            Catch : End Try
                            Try
                                Dim propM As AssetValue = oAsset("generic_metallic")
                                If propM IsNot Nothing Then CType(propM, FloatAssetValue).Value = metallic
                            Catch : End Try
                            Try
                                Dim propCc As AssetValue = oAsset("generic_clearcoat")
                                If propCc IsNot Nothing Then CType(propCc, FloatAssetValue).Value = 0.0
                            Catch : End Try
                        End If
                    Next
                    Try : targetDoc.Update() : Catch : End Try
                Catch : End Try
            Next

            ' Cập nhật khung nhìn
            Try : oDoc.Update() : Catch : End Try
            Try : oView.Update() : Catch : End Try

        Catch ex As Exception
            MessageBox.Show("Loi phat sinh: " & ex.Message, "Loi Dark Cinematic Studio", MessageBoxButtons.OK, MessageBoxIcon.Error)
        Finally
            oApp.SilentOperation = False
        End Try

        ' ==============================================================================
        ' 7. THÔNG BÁO HOÀN TẤT THIẾT LẬP DARK CINEMATIC STUDIO
        ' ==============================================================================
        MessageBox.Show("🎬 ĐÃ THIẾT LẬP THÀNH CÔNG: WT3D DARK CINEMATIC STUDIO!" & vbCrLf & _
                        "━━━━━━━━━━━━━━━━━━━━━━━━━━━━━━━━━━━━━━━━━━━━━━━━━" & vbCrLf & _
                        "• Phông nền: Color Scheme 'Dark Sky' (Gradient than chì sâu thẳm)" & vbCrLf & _
                        "• Ánh sáng tổng thể: Brightness 58% | Ambience 14% (Tương phản cao điện ảnh)" & vbCrLf & _
                        "• Đèn chính (Key): 95% (Trắng ấm 4800K) | Đèn phụ (Fill): 35% (Xanh thép 7000K)" & vbCrLf & _
                        "• Đèn viền lưng (Dramatic Rim Light): 125% (Tạo viền bạc sắc lẹm tách nền đen)" & vbCrLf & _
                        "• Đèn trần (Top Accent): 40% (Rọi sáng sống lưng máy và đồng hồ áp)" & vbCrLf & _
                        "• Mặt sàn triển lãm: Bóng đổ đậm (65%) + Phản xạ gương sàn mờ ảo (Wet Floor)" & vbCrLf & _
                        "• Tối ưu vật liệu PBR: Tăng cường phản xạ viền kim loại Inox 95% cực nét." & vbCrLf & _
                        "👉 Phù hợp nhất: Video TikTok/Reels, ảnh bìa công nghệ cao, phong cách Dark Mode!", _
                        "WT3D Dark Cinematic Studio Rig", MessageBoxButtons.OK, MessageBoxIcon.Information)
    End Sub
End Class
