AddReference "PresentationCore"
AddReference "WindowsBase"
AddReference "System.Drawing"
AddReference "System.Private.Windows.GdiPlus"
AddReference "System.Windows.Forms"
AddReference "System.Private.Windows.Core"

Imports System.Windows.Input

' ==============================================================================
' MAXSKILLS V5 - SUPERCAR DRONE SHOT (ILOGIC CAMERA ENGINE)
' ==============================================================================

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Dim oApp As Inventor.Application = ThisApplication
        Dim oDoc As Document = oApp.ActiveDocument
        Dim oView As Inventor.View = oApp.ActiveView
        Dim oCam As Camera = oView.Camera
        Dim tg As TransientGeometry = oApp.TransientGeometry

        If oDoc.DocumentType <> DocumentTypeEnum.kAssemblyDocumentObject And oDoc.DocumentType <> DocumentTypeEnum.kPartDocumentObject Then
            ' ' _MUTED_BY_AI_MessageBox_Show("Vui lòng mở file Assembly (Cụm máy) hoặc Part để quay!", "Supercar Engine")
            Exit Sub
        End If

        ' --- CẤU HÌNH ĐỘ PHÂN GIẢI 4K ULTRA-HD (2160 x 3840 FOR SHORTS 9:16) ---
        Dim renderW As Integer = 2160
        Dim renderH As Integer = 3840

        ' ============================================================
        ' 🧠 AUTO-GENERATE SEO METADATA (ZERO-TOUCH - Chạy trước render)
        ' Đảm bảo Dashboard_SEO & Z_Copy_Paste_SEO_Data.txt luôn mới nhất
        ' ============================================================
        Dim isBatch As Boolean = False
        Try : isBatch = SharedVariable("BatchMode") : Catch : End Try

        If Not isBatch Then
            ThisApplication.StatusBarText = "🧠 CAM 3: Generating SEO Metadata..."
            Try : iLogicVb.RunExternalRule("d:\WT3D_Project\Z_Tools\Auto_SEO_Metadata_Engine.iLogicVb") : Catch : End Try
        End If
        ThisApplication.StatusBarText = "🎥 CAM 3: Starting render..."
        ' ============================================================

        ' --- LƯU TRẠNG THÁI CAMERA GỐC ---
        Dim oTg2 As TransientGeometry = ThisApplication.TransientGeometry
        Dim orgEyeX = oCam.Eye.X, orgEyeY = oCam.Eye.Y, orgEyeZ = oCam.Eye.Z
        Dim orgTgx = oCam.Target.X, orgTgy = oCam.Target.Y, orgTgz = oCam.Target.Z
        Dim orgUpX = oCam.UpVector.X, orgUpY = oCam.UpVector.Y, orgUpZ = oCam.UpVector.Z
        Dim orgPersp = oCam.Perspective
        Dim orgPerspAng = 0.0
        Try
            orgPerspAng = oCam.PerspectiveAngle
        Catch
        End Try
        ' -----------------------------------

        ' 1. LẤY TỌA ĐỘ VÀ KÍCH THƯỚC BAO QUANH (BOUNDING BOX)
        Dim rb = oDoc.ComponentDefinition.RangeBox
        Dim minX = rb.MinPoint.X, minY = rb.MinPoint.Y, minZ = rb.MinPoint.Z
        Dim maxX = rb.MaxPoint.X, maxY = rb.MaxPoint.Y, maxZ = rb.MaxPoint.Z

        Dim cx = (minX + maxX) / 2
        Dim cy = (minY + maxY) / 2
        Dim cz = (minZ + maxZ) / 2

        Dim dx = maxX - minX
        Dim dy = maxY - minY
        Dim dz = maxZ - minZ
        Dim max_dim = Math.Max(dx, Math.Max(dy, dz))

        ' --- SETUP M?I TR??NG ?NH S?NG & ?? B?NG ---
        Try
            oView.ShowShadows = True
            oView.ShowAmbientShadows = True
            oView.ShowObjectShadows = True
            oView.ShowGroundReflections = False
            oDoc.ActiveLightingStyle = oDoc.LightingStyles.Item("Dark Sky")
        Catch
            Try : oDoc.ActiveLightingStyle = oDoc.LightingStyles.Item("Empty Lab") : Catch : End Try
        End Try
        ' -----------------------------------------

        ' --- XUÁT VIDEO FRAMES ---
        Dim tempPath = "d:\WT3D_Project\2_Video_Renders\"
        If Not System.IO.Directory.Exists(tempPath) Then System.IO.Directory.CreateDirectory(tempPath)
        Dim saveFolder = tempPath & System.IO.Path.GetFileNameWithoutExtension(oDoc.FullFileName) & "_CAM_3"
        If Not System.IO.Directory.Exists(saveFolder) Then System.IO.Directory.CreateDirectory(saveFolder)
        Dim frameCount = 1
        ' -------------------------

        ' Bật chất lượng hiển thị Shaded With Edges cực sắc nếu đang ở chế độ khác
        Try
            oView.DisplayMode = DisplayModeEnum.kShadedWithEdgesRendering
            oView.Update()
        Catch
        End Try

        ' ==============================================================================
        ' THUẬT TOÁN ĐA CẢNH "SUPERCAR ADVERTISEMENT" (8 CUTS x 15 GIÂY SHORTS)
        ' ==============================================================================
        ' ' _MUTED_BY_AI_MessageBox_Show("🔥 ĐẠO DIỄN LÊN TOOL: 8 CẢNH FAST-CUT QUẢNG CÁO (CHUẨN 15s SHORTS)! " & vbCrLf & "Clip sẽ dồn dập chuyển cảnh liên tục để giữ chân người xem TikTok/YouTube Short.", "MAXSKILLS Director")

        Dim upVec = tg.CreateUnitVector(0, 1, 0)
        oCam.UpVector = upVec

        Dim isAborted As Boolean = False
        Dim orgDispMode = oView.DisplayMode
        Try : oView.DisplayMode = DisplayModeEnum.kShadedWithEdgesRendering : oView.Update() : Catch : End Try
        oCam.Perspective = True

        ' === SCENE 1: Close Supercar Perspective Launch (35f - Quintic Easing) ===
        Try : oView.DisplayMode = DisplayModeEnum.kShadedWithEdgesRendering : oView.Update() : Catch : End Try
        oCam.Perspective = True
        Dim fMax1 As Integer = 35
        For i = 1 To fMax1
            Dim fMax As Double = CDbl(fMax1)
            Dim t = i / fMax : Dim e = t * t * t * (t * (t * 6.0 - 15.0) + 10.0)
            Dim theta = Math.PI * 0.25 + (Math.PI * 0.15) * e
            Dim curR = max_dim * (0.78 - 0.20 * e)
            Dim gimbalRoll = Math.Sin(Math.PI * e) * 0.04
            oCam.Eye = tg.CreatePoint(cx + curR * Math.Cos(theta), cy + dy * 0.1, cz + curR * Math.Sin(theta))
            oCam.Target = tg.CreatePoint(cx, cy, cz)
            oCam.PerspectiveAngle = 0.52
            oCam.UpVector = tg.CreateUnitVector(gimbalRoll, 1.0, 0.0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 2: FPV Fast High Dive (30f - Dynamic Roll) ===
        Try : oView.DisplayMode = DisplayModeEnum.kShadedWithEdgesRendering : oView.Update() : Catch : End Try
        Dim fMax2 As Integer = 30
        For i = 1 To fMax2
            Dim fMax As Double = CDbl(fMax2)
            Dim t = i / fMax : Dim e = t * t * t * (t * (t * 6.0 - 15.0) + 10.0)
            Dim dropY = cy + max_dim * 0.6 - max_dim * 0.4 * e
            Dim theta = Math.PI * 0.25 + Math.PI * 0.6 * e
            Dim curR = max_dim * (0.75 - 0.25 * e)
            Dim gimbalRoll = -Math.Sin(Math.PI * e) * 0.05
            oCam.Eye = tg.CreatePoint(cx + curR * Math.Cos(theta), dropY, cz + curR * Math.Sin(theta))
            oCam.Target = tg.CreatePoint(cx, cy, cz)
            oCam.PerspectiveAngle = 0.52
            oCam.UpVector = tg.CreateUnitVector(gimbalRoll, 1.0, 0.0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 3: Whip Reverse Dolly Close-Up (30f - Smoothstep) ===
        Try : oView.DisplayMode = DisplayModeEnum.kWireframeNoHiddenEdges : oView.Update() : Catch : End Try
        Dim fMax3 As Integer = 30
        For i = 1 To fMax3
            Dim fMax As Double = CDbl(fMax3)
            Dim t = i / fMax : Dim e = t * t * t * (t * (t * 6.0 - 15.0) + 10.0)
            Dim curR = max_dim * (0.35 + 0.35 * e)
            oCam.Eye = tg.CreatePoint(cx + curR * Math.Cos(Math.PI*0.35), cy + dy*0.1, cz + curR * Math.Sin(Math.PI*0.35))
            oCam.Target = tg.CreatePoint(cx, cy, cz)
            oCam.PerspectiveAngle = 0.50
            oCam.UpVector = tg.CreateUnitVector(0, 1, 0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 4: Ground Drift Base Scan (30f - Dynamic Roll) ===
        Try : oView.DisplayMode = DisplayModeEnum.kShadedWithEdgesRendering : oView.Update() : Catch : End Try
        Dim fMax4 As Integer = 30
        For i = 1 To fMax4
            Dim fMax As Double = CDbl(fMax4)
            Dim t = i / fMax : Dim e = t * t * t * (t * (t * 6.0 - 15.0) + 10.0)
            Dim theta = Math.PI * 0.15 + (Math.PI * 0.4) * e
            Dim curR = max_dim * 0.60
            Dim gimbalRoll = Math.Sin(Math.PI * e) * 0.04
            oCam.Eye = tg.CreatePoint(cx + curR * Math.Cos(theta), cy - dy*0.15, cz + curR * Math.Sin(theta))
            oCam.Target = tg.CreatePoint(cx, cy, cz)
            oCam.PerspectiveAngle = 0.54
            oCam.UpVector = tg.CreateUnitVector(gimbalRoll, 1.0, 0.0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 5: High 3/4 Crane Dive (30f - Smoothstep) ===
        Try : oView.DisplayMode = DisplayModeEnum.kShadedWithEdgesRendering : oView.Update() : Catch : End Try
        oCam.Perspective = True
        Dim fMax5 As Integer = 30
        For i = 1 To fMax5
            Dim fMax As Double = CDbl(fMax5)
            Dim t = i / fMax : Dim e = t * t * t * (t * (t * 6.0 - 15.0) + 10.0)
            Dim theta = Math.PI * 0.75 + (Math.PI * 0.40) * e
            Dim elev = Math.PI * 0.22
            Dim curR = max_dim * 0.65
            oCam.Eye = tg.CreatePoint(cx + curR * Math.Cos(elev) * Math.Cos(theta), cy + curR * Math.Sin(elev) + (dy * 0.1), cz + curR * Math.Cos(elev) * Math.Sin(theta))
            oCam.Target = tg.CreatePoint(cx, cy, cz)
            oCam.PerspectiveAngle = 0.52
            oCam.UpVector = tg.CreateUnitVector(0, 1, 0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 6: Back-Right 3/4 Macro Orbit (30f - Smoothstep) ===
        Try : oView.DisplayMode = DisplayModeEnum.kShadedWithEdgesRendering : oView.Update() : Catch : End Try
        Dim fMax6 As Integer = 30
        For i = 1 To fMax6
            Dim fMax As Double = CDbl(fMax6)
            Dim t = i / fMax : Dim e = t * t * t * (t * (t * 6.0 - 15.0) + 10.0)
            Dim theta = Math.PI * 1.15 + (Math.PI * 0.40) * e
            Dim curR = max_dim * 0.55
            oCam.Eye = tg.CreatePoint(cx + curR * Math.Cos(theta), cy + dy * 0.05, cz + curR * Math.Sin(theta))
            oCam.Target = tg.CreatePoint(cx, cy, cz)
            oCam.PerspectiveAngle = 0.50
            oCam.UpVector = tg.CreateUnitVector(0, 1, 0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        ' === SCENE 7: Hero 3/4 Perspective Full Screen Finale (45f - Smoothstep) ===
        Try : oView.DisplayMode = DisplayModeEnum.kShadedWithEdgesRendering : oView.Update() : Catch : End Try
        oCam.Perspective = True
        Dim fMax7 As Integer = 45
        For i = 1 To fMax7
            Dim fMax As Double = CDbl(fMax7)
            Dim t = i / fMax : Dim e = t * t * t * (t * (t * 6.0 - 15.0) + 10.0)
            Dim theta = Math.PI * 1.55 + (Math.PI * 0.50) * e
            Dim curR = max_dim * (0.48 + 0.05 * e)
            oCam.Eye = tg.CreatePoint(cx + curR * Math.Cos(theta), cy + dy * 0.1, cz + curR * Math.Sin(theta))
            oCam.Target = tg.CreatePoint(cx, cy, cz)
            oCam.PerspectiveAngle = 0.54
            oCam.UpVector = tg.CreateUnitVector(0, 1, 0)
            oCam.ApplyWithoutTransition() : If CheckEscape() Then
                    ThisApplication.StatusBarText = "🛑 ĐÃ DỪNG TIẾN TRÌNH THEO LỆNH (GIỮ PHÍM ESC)!"
                    Exit Sub
                End If
                SafeYield(20)
            oCam.SaveAsBitmap(saveFolder & "\frame_" & frameCount.ToString("0000") & ".png", renderW, renderH) : frameCount += 1
            If CheckEscape() Then
                    ThisApplication.StatusBarText = "🛑 ĐÃ DỪNG TIẾN TRÌNH THEO LỆNH (GIỮ PHÍM ESC)!"
                    Exit Sub
                End If
                SafeYield(20)
            If System.Windows.Input.Keyboard.IsKeyDown(System.Windows.Input.Key.Escape) Then : isAborted = True : GoTo AbortCamera : End If
        Next

        GoTo NormalCompletion
        AbortCamera:
            MessageBox.Show("🛑 HỦY RENDER THÀNH CÔNG! Đã dừng việc chụp ảnh và xuất FFmpeg.", "Ngắt Khẩn Cấp B2B")
            Try : oView.DisplayMode = orgDispMode : Catch : End Try
            oCam.Eye = oTg2.CreatePoint(orgEyeX, orgEyeY, orgEyeZ)
            oCam.Target = oTg2.CreatePoint(orgTgx, orgTgy, orgTgz)
            oCam.UpVector = oTg2.CreateUnitVector(orgUpX, orgUpY, orgUpZ)
            oCam.Perspective = orgPersp
            If orgPersp Then : Try : oCam.PerspectiveAngle = orgPerspAng : Catch : End Try : End If
            oCam.Apply() : oView.Update()
            Exit Sub

        NormalCompletion:
        Try : oView.DisplayMode = orgDispMode : Catch : End Try



        RestoreCamera:
        ' --- TRẢ VỀ CAMERA GỐC ---
        oCam.Eye = oTg2.CreatePoint(orgEyeX, orgEyeY, orgEyeZ)
        oCam.Target = oTg2.CreatePoint(orgTgx, orgTgy, orgTgz)
        oCam.UpVector = oTg2.CreateUnitVector(orgUpX, orgUpY, orgUpZ)
        oCam.Perspective = orgPersp
        If orgPersp Then
            Try : oCam.PerspectiveAngle = orgPerspAng : Catch : End Try
        End If
        oCam.Apply()
        oView.Update()
        Try : Dim sh As Object = CreateObject("WScript.Shell") : sh.Run("powershell.exe -ExecutionPolicy Bypass -WindowStyle Hidden -File d:\WT3D_Project\Z_Tools\Auto_Stitch_Master.ps1", 0, True) : Catch : End Try

        Dim _baseName As String = System.IO.Path.GetFileNameWithoutExtension(oDoc.FullFileName)
        Dim _videoDir As String = "d:\WT3D_Project\2_Video_Renders"
        If Not isBatch Then
            Try : Process.Start("explorer.exe", _videoDir) : Catch : End Try
            Try : Process.Start("explorer.exe", saveFolder) : Catch : End Try
            ThisApplication.StatusBarText = "✅ CAM 3 HOÀN TẤT! Folder Video & Frames đã mở sẵn."
        End If
    End Sub
End Class
