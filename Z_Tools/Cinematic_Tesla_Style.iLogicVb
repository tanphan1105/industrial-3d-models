AddReference "PresentationCore"
AddReference "WindowsBase"
AddReference "System.Drawing"
AddReference "System.Private.Windows.GdiPlus"
AddReference "System.Windows.Forms"
AddReference "System.Private.Windows.Core"

Imports System.Windows.Input

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Try
            ' ================================================================
            ' TESLA STYLE: "Aggressive Predator"
            ' Triết lý: Gắt - Hard Cut - Worm Eye - Cú đâm thẳng kiểu Tesla
            ' DNA: EaseOut mạnh, nhiều Hard Cut, góc thấp áp đảo, Linear nhanh
            ' Tổng: 240 frames / 30fps = 8 giây
            ' ================================================================
            Dim oDoc As Inventor.Document = ThisDoc.Document
            Dim baseName As String = System.IO.Path.GetFileNameWithoutExtension(oDoc.FullFileName)
            Dim masterDir As String = "d:\WT3D_Project"
            Dim saveFolder As String = "d:\WT3D_Project\2_Video_Renders\TESLA_" & baseName
            If Not System.IO.Directory.Exists(saveFolder) Then System.IO.Directory.CreateDirectory(saveFolder)
            For Each f In System.IO.Directory.GetFiles(saveFolder, "*.png")
                Try : System.IO.File.Delete(f) : Catch : End Try
            Next

            Dim tg As TransientGeometry = ThisApplication.TransientGeometry
            Dim oView As Inventor.View = ThisApplication.ActiveView
            Dim oCam As Inventor.Camera = oView.Camera
            oCam.Perspective = True

            ' =======================================================
            ' ENGINE ÁNH SÁNG CAO CẤP (CINEMATIC PREMIUM LIGHTING)
            ' =======================================================
            Try
                oDoc.ObjectVisibility.AllWorkFeatures = False ' Tắt trục tọa độ rác
                oDoc.ObjectVisibility.Sketches = False
                oDoc.ObjectVisibility.Sketches3D = False
            Catch
            End Try

            oView.DisplayMode = DisplayModeEnum.kShadedRendering ' Xóa Viền Đen (Kiểu Bản Vẽ) để mô hình chân thật 100%
            oView.ShowAmbientShadows = True
            oView.ShowObjectShadows = True       ' Bóng đổ vật lý lên chính thân máy (Tạo khối 3D)
            oView.ShowGroundShadows = True       ' Đổ bóng đen xuống sàn nền
            oView.ShowGroundReflections = True   ' Sàn gương kính bóng loáng cực kỳ sang trọng
            ThisApplication.ColorSchemes.BackgroundType = BackgroundTypeEnum.kGradientBackgroundType

            Dim rBox As Inventor.Box = oDoc.ComponentDefinition.RangeBox
            Dim maxDim As Double = Math.Max(rBox.MaxPoint.X - rBox.MinPoint.X, Math.Max(rBox.MaxPoint.Y - rBox.MinPoint.Y, rBox.MaxPoint.Z - rBox.MinPoint.Z))

            ' TRÍ TUỆ NHÂN TẠO P1: KHÓA MỤC TIÊU VÀO TRÁI TIM VẬT LÝ (CENTER OF MASS)
            ' Thay vì nhìn vào một cái hộp vô hồn, Camera tự động Focus vào khu vực Nặng Nhất, Chứa nhiều linh kiện hất của Cụm máy.
            Dim cX As Double = (rBox.MaxPoint.X + rBox.MinPoint.X) / 2
            Dim cY As Double = (rBox.MaxPoint.Y + rBox.MinPoint.Y) / 2
            Dim cZ As Double = (rBox.MaxPoint.Z + rBox.MinPoint.Z) / 2
            Try
                Dim com As Inventor.Point = oDoc.ComponentDefinition.MassProperties.CenterOfMass
                cX = com.X : cY = com.Y : cZ = com.Z 
            Catch
            End Try

            Dim fc As Integer = 1
            Dim isSkid As Boolean = (maxDim > 50)

            If isSkid Then
                ' ================================================================
                ' TESLA STYLE DÀNH CHO CẢ MÁY LỚN & VỪA (> 0.5 Mét)
                ' ================================================================
                ' KHAI BÁO TỌA ĐỘ VÀNG TỪ INVENTOR NATIVE VIEWCUBE
                ' Lấy chính xác góc nhìn chuẩn Isometric Top Right nguyên bản của Inventor
                ' ================================================================
                oCam.ViewOrientationType = ViewOrientationTypeEnum.kIsoTopRightViewOrientation
                oCam.Perspective = True
                oCam.ApplyWithoutTransition()
                oCam.Fit()
                oCam.ApplyWithoutTransition()

                Dim camW As Double, camH As Double
                oCam.GetExtents(camW, camH)
                oCam.SetExtents(camW * 1.5, camH * 1.5) ' Hệ số 1.5x để bù không gian cho thanh đen rạp phim
                oCam.ApplyWithoutTransition()

                Dim fitEye As Inventor.Point = tg.CreatePoint(oCam.Eye.X, oCam.Eye.Y, oCam.Eye.Z)
                Dim fitTarget As Inventor.Point = tg.CreatePoint(oCam.Target.X, oCam.Target.Y, oCam.Target.Z)

                ' Tọa độ Đích của cú phóng phi tiêu Worm Eye
                Dim destTheta As Double = Math.PI * 0.8
                Dim destR As Double = maxDim * 1.0
                Dim destEyeY As Double = cY + maxDim * 0.05
                Dim destEye As Inventor.Point = tg.CreatePoint(cX + destR * Math.Cos(destTheta), destEyeY, cZ + destR * Math.Sin(destTheta))
                Dim destTarget As Inventor.Point = tg.CreatePoint(cX, cY + maxDim * 0.2, cZ)

                ' ── CẢNH 1 (25f): NATIVE VIEWCUBE FIT -> WORM EYE DIVE ──
                For i As Integer = 1 To 25
                    Dim t As Double = i / 25.0
                    Dim e As Double = Math.Pow(t, 2)

                    Dim curEye As Inventor.Point = tg.CreatePoint( _
                        fitEye.X + (destEye.X - fitEye.X) * e, _
                        fitEye.Y + (destEye.Y - fitEye.Y) * e, _
                        fitEye.Z + (destEye.Z - fitEye.Z) * e)

                    Dim curTarget As Inventor.Point = tg.CreatePoint( _
                        fitTarget.X + (destTarget.X - fitTarget.X) * e, _
                        fitTarget.Y + (destTarget.Y - fitTarget.Y) * e, _
                        fitTarget.Z + (destTarget.Z - fitTarget.Z) * e)

                    oCam.Eye = curEye
                    oCam.Target = curTarget
                    oCam.UpVector = tg.CreateUnitVector(0, 1, 0)
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[TESLA V5] 1/7 - ViewCube Drop: " & i & "/25"
                Next

                ' ── CẢNH 2 (20f): DOLLY STRIKE ──
                Dim ang2 As Double = Math.PI * 0.8
                For i As Integer = 1 To 20
                    Dim t As Double = i / 20.0
                    Dim e As Double = 1 - Math.Pow(1 - t, 4)
                    Dim R As Double = maxDim * (1.0 - 0.6 * e)
                    Dim eyeY As Double = cY + maxDim * 0.3
                    oCam.Eye = tg.CreatePoint(cX + R * Math.Cos(ang2), eyeY, cZ + R * Math.Sin(ang2))
                    oCam.Target = tg.CreatePoint(cX, cY, cZ)
                    oCam.UpVector = tg.CreateUnitVector(0, 1, 0)
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[TESLA V5] 2/7 - Dolly Strike: " & i & "/20"
                Next

                ' ── CẢNH 3 (15f) [NEW]: PUNCH-IN DETAIL (Hard Cut vào góc chéo) ──
                Dim ang3 As Double = Math.PI * 0.35
                For i As Integer = 1 To 15
                    Dim t As Double = i / 15.0
                    Dim R As Double = maxDim * 0.35
                    oCam.Eye = tg.CreatePoint(cX + R * Math.Cos(ang3), cY + maxDim * 0.4, cZ + R * Math.Sin(ang3))
                    oCam.Target = tg.CreatePoint(cX - maxDim * 0.1, cY + maxDim * 0.2, cZ + maxDim * 0.1) ' Lệch tâm tạo chiều sâu
                    oCam.UpVector = tg.CreateUnitVector(0, 1, 0)
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[TESLA V5] 3/7 - Punch Detail: " & i & "/15"
                Next

                ' ── CẢNH 4 (40f): AXIS FLY-AROUND (Khoáy lệch trục nhanh hơn) ──
                Dim ang4 As Double = ang3 + Math.PI
                For i As Integer = 1 To 40
                    Dim t As Double = i / 40.0
                    Dim theta As Double = ang4 + (Math.PI * 1.2) * t ' Khoáy cực nhanh 1.2 x 180 độ
                    Dim R As Double = maxDim * 1.5
                    Dim eyeY As Double = cY + maxDim * (0.2 + 0.6 * t)
                    oCam.Eye = tg.CreatePoint(cX + R * Math.Cos(theta), eyeY, cZ + R * Math.Sin(theta))
                    oCam.Target = tg.CreatePoint(cX, cY, cZ)
                    oCam.UpVector = tg.CreateUnitVector(0, 1, 0)
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[TESLA V5] 4/7 - Axis Fly: " & i & "/40"
                Next

                ' ── CẢNH 5 (30f) [NEW]: TOP DOWN DRILL (Bổ nhào lốc xoáy) ──
                Dim ang5 As Double = ang4 + Math.PI * 1.2
                For i As Integer = 1 To 30
                    Dim t As Double = i / 30.0
                    Dim e As Double = Math.Pow(t, 2)
                    Dim spin As Double = ang5 + (Math.PI / 2.0) * e
                    oCam.Eye = tg.CreatePoint(cX + 0.001, cY + maxDim * 2.0 - maxDim * 1.0 * e, cZ)
                    oCam.Target = tg.CreatePoint(cX, cY, cZ)
                    oCam.UpVector = tg.CreateUnitVector(Math.Cos(spin), 0, Math.Sin(spin))
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[TESLA V5] 5/7 - Top Drill: " & i & "/30"
                Next

                ' ── CẢNH 6 (40f): WORM CREEP + DUTCH WHIP (Bò sát đất + Khung hình chéo) ──
                Dim ang6 As Double = Math.PI * 1.7
                For i As Integer = 1 To 40
                    Dim t As Double = i / 40.0
                    Dim e As Double = Math.Pow(t, 0.4)
                    Dim R As Double = maxDim * (0.6 - 0.1 * e)
                    Dim theta As Double = ang6 + (Math.PI / 8.0) * e
                    Dim eyeY As Double = cY + maxDim * 0.05
                    oCam.Eye = tg.CreatePoint(cX + R * Math.Cos(theta), eyeY, cZ + R * Math.Sin(theta))
                    oCam.Target = tg.CreatePoint(cX, cY + maxDim * 0.5, cZ)
                    oCam.UpVector = tg.CreateUnitVector(0.15, 1, 0) ' Nghiêng ống kính 15 độ
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[TESLA V5] 6/7 - Dutch Creep: " & i & "/40"
                Next

                ' Tọa độ điểm dừng của Cảnh 6 để Cảnh 7 nối tiếp rút ra
                Dim ang6_end As Double = Math.PI * 1.7 + Math.PI / 8.0
                Dim R6_end As Double = maxDim * 0.5
                Dim eyeY6_end As Double = cY + maxDim * 0.05
                Dim startEye7 As Inventor.Point = tg.CreatePoint(cX + R6_end * Math.Cos(ang6_end), eyeY6_end, cZ + R6_end * Math.Sin(ang6_end))
                Dim startTarget7 As Inventor.Point = tg.CreatePoint(cX, cY + maxDim * 0.5, cZ) ' Cảnh 6 mục tiêu là cY+0.5

                ' ── CẢNH 7 (70f): EXPLOSIVE EXIT VỀ ĐÚNG GÓC NGUYÊN BẢN (ViewCube Loop) ──
                For i As Integer = 1 To 70
                    Dim t As Double = i / 70.0
                    Dim e As Double = 1 - Math.Pow(1 - t, 3) 

                    Dim curEye As Inventor.Point = tg.CreatePoint( _
                        startEye7.X + (fitEye.X - startEye7.X) * e, _
                        startEye7.Y + (fitEye.Y - startEye7.Y) * e, _
                        startEye7.Z + (fitEye.Z - startEye7.Z) * e)

                    Dim curTarget As Inventor.Point = tg.CreatePoint( _
                        startTarget7.X + (fitTarget.X - startTarget7.X) * e, _
                        startTarget7.Y + (fitTarget.Y - startTarget7.Y) * e, _
                        startTarget7.Z + (fitTarget.Z - startTarget7.Z) * e)

                    oCam.Eye = curEye
                    oCam.Target = curTarget
                    ' Nhả mượt mà góc camera bị nghiêng (Dutch 15 độ) trở về thăng bằng đứng thẳng (0 độ)
                    oCam.UpVector = tg.CreateUnitVector(0.15 * (1 - e), 1, 0)
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[TESLA V5] 7/7 - Loop Exit to ViewCube: " & i & "/70"
                Next
            Else
                ' =====================================================================
                ' SMART MACRO STYLE DÀNH CHO THIẾT BỊ NHỎ (< 1.5 Mét)
                ' Chống vỡ khung và chống bay lề khi quét các linh kiện bé
                ' =====================================================================
                ' CẢNH 1 (60f): TURNTABLE NHANH 180° - Linear
                For i As Integer = 1 To 60
                    Dim t As Double = i / 60.0
                    Dim theta As Double = Math.PI * t
                    Dim eyeY As Double = cY + maxDim * 0.4
                    oCam.Eye = tg.CreatePoint(cX + maxDim * 1.8 * Math.Cos(theta), eyeY, cZ + maxDim * 1.8 * Math.Sin(theta))
                    oCam.Target = tg.CreatePoint(cX, cY, cZ)
                    oCam.UpVector = tg.CreateUnitVector(0, 1, 0)
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[MACRO] C1 - Turntable: " & i & "/60"
                Next

                ' CẢNH 2 (50f): MACRO ZOOM - EaseOut (lao vào sát)
                For i As Integer = 1 To 50
                    Dim t As Double = i / 50.0
                    Dim t_ease As Double = 1 - (1 - t) * (1 - t)
                    Dim R As Double = maxDim * (1.8 - 1.1 * t_ease)
                    Dim eyeY As Double = cY + maxDim * (0.4 - 0.25 * t_ease)
                    oCam.Eye = tg.CreatePoint(cX + R * Math.Cos(Math.PI), eyeY, cZ + R * Math.Sin(Math.PI))
                    oCam.Target = tg.CreatePoint(cX, cY, cZ)
                    oCam.UpVector = tg.CreateUnitVector(0, 1, 0)
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[MACRO] C2 - Macro Strike: " & i & "/50"
                Next

                ' CẢNH 3 (60f): ORBIT CHẬM 90° TỪ DƯỚI - SmoothStep
                For i As Integer = 1 To 60
                    Dim t As Double = i / 60.0
                    Dim t_ease As Double = t * t * (3 - 2 * t)
                    Dim theta As Double = Math.PI + (Math.PI / 2.0) * t_ease
                    Dim eyeY As Double = cY + maxDim * (0.15 + 0.35 * t_ease)
                    oCam.Eye = tg.CreatePoint(cX + maxDim * 0.7 * Math.Cos(theta), eyeY, cZ + maxDim * 0.7 * Math.Sin(theta))
                    oCam.Target = tg.CreatePoint(cX, cY, cZ)
                    oCam.UpVector = tg.CreateUnitVector(0, 1, 0)
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[MACRO] C3 - Low Orbit: " & i & "/60"
                Next

                ' CẢNH 4 (70f): PULL BACK HERO - EaseInOut
                For i As Integer = 1 To 70
                    Dim t As Double = i / 70.0
                    Dim t_ease As Double = t * t * (3 - 2 * t)
                    Dim theta As Double = Math.PI * 1.5
                    Dim R As Double = maxDim * (0.7 + 1.5 * t_ease)
                    Dim eyeY As Double = cY + maxDim * (0.5 + 0.5 * t_ease)
                    oCam.Eye = tg.CreatePoint(cX + R * Math.Cos(theta), eyeY, cZ + R * Math.Sin(theta))
                    oCam.Target = tg.CreatePoint(cX, cY, cZ)
                    oCam.UpVector = tg.CreateUnitVector(0, 1, 0)
                    oCam.ApplyWithoutTransition()
                    oCam.SaveAsBitmap(saveFolder & "\frame_" & fc.ToString("000") & ".png", 2560, 1440)

                If CheckEscape() Then
                    ThisApplication.StatusBarText = "🛑 ĐÃ DỪNG TIẾN TRÌNH THEO LỆNH (GIỮ PHÍM ESC)!"
                    Exit Sub
                End If
                SafeYield(20)
                    fc += 1 : ThisApplication.StatusBarText = "[MACRO] C4 - Hero Shot: " & i & "/70"
                Next
            End If

            ThisApplication.StatusBarText = "CINEMATIC MASTER - HOÀN TẤT CAMERA!"

            ' =======================================================
            ' GENERATE MASTER WATERMARK OVERLAY (LOCKED 4-LAYER SPECIFICATION)
            ' =======================================================
            Dim wmkPath As String = saveFolder & "\watermark.png"
            If System.IO.File.Exists(wmkPath) Then System.IO.File.Delete(wmkPath)

            Using wmkBmp As New System.Drawing.Bitmap(2560, 1440)
                Using g As System.Drawing.Graphics = System.Drawing.Graphics.FromImage(wmkBmp)
                    g.SmoothingMode = System.Drawing.Drawing2D.SmoothingMode.HighQuality
                    g.InterpolationMode = System.Drawing.Drawing2D.InterpolationMode.HighQualityBicubic
                    g.PixelOffsetMode = System.Drawing.Drawing2D.PixelOffsetMode.HighQuality
                    g.TextRenderingHint = System.Drawing.Text.TextRenderingHint.AntiAliasGridFit

                    ' HOLLYWOOD CINEMASCOPE LETTERBOX (2.35:1)
                    Dim barH As Integer = 175
                    Using blackBrush As New System.Drawing.SolidBrush(System.Drawing.Color.Black)
                        g.FillRectangle(blackBrush, 0, 0, 2560, barH)
                        g.FillRectangle(blackBrush, 0, 1440 - barH, 2560, barH)
                    End Using

                    ' ------------------------------------------------------------------
                    ' LỚP 1: LÁ CỜ VIỆT NAM (GÓC TRÊN BÊN TRÁI)
                    ' ------------------------------------------------------------------
                    Dim flagW As Single = 2560.0F * 0.105F
                    Dim flagH As Single = flagW * 0.6667F
                    Dim flagX As Single = 2560.0F * 0.030F
                    Dim flagY As Single = 1440.0F * 0.030F
                    Dim flagPath As String = masterDir & "\Z_Tools\vietnam_flag.png"
                    If System.IO.File.Exists(flagPath) Then
                        Try
                            Dim flagBytes As Byte() = System.IO.File.ReadAllBytes(flagPath)
                            Using flagMs As New System.IO.MemoryStream(flagBytes)
                                Using flagImg As New System.Drawing.Bitmap(flagMs)
                                    g.DrawImage(flagImg, flagX, flagY, flagW, flagH)
                                End Using
                            End Using
                        Catch : End Try
                    End If

                    ' ------------------------------------------------------------------
                    ' LỚP 2: BẢN QUYỀN THỦY TINH CHÍNH GIỮA MÀN HÌNH (@tanphan1105)
                    ' ------------------------------------------------------------------
                    Dim mailY As Single = 1440.0F * 0.44F
                    g.TranslateTransform(2560.0F / 2.0F, mailY)
                    Dim mailText As String = "@tanphan1105"
                    Dim mailSize As Single = 2560.0F * 0.052F
                    Using mailFont As New System.Drawing.Font("Arial Black", mailSize, System.Drawing.FontStyle.Bold)
                        Using gp2 As New System.Drawing.Drawing2D.GraphicsPath()
                            Dim sf2 As New System.Drawing.StringFormat() 
                            sf2.Alignment = System.Drawing.StringAlignment.Center
                            sf2.LineAlignment = System.Drawing.StringAlignment.Center
                            gp2.AddString(mailText, mailFont.FontFamily, CInt(mailFont.Style), mailFont.Size, New System.Drawing.PointF(0, 0), sf2)
                            Dim pThick2 As Single = Math.Max(1.0F, 2560.0F * 0.0015F)
                            Using darkPen2 As New System.Drawing.Pen(System.Drawing.Color.FromArgb(35, 0, 0, 0), pThick2)
                                g.TranslateTransform(pThick2, pThick2)
                                g.DrawPath(darkPen2, gp2)
                                g.TranslateTransform(-pThick2, -pThick2)
                            End Using
                            Using glassBrush As New System.Drawing.SolidBrush(System.Drawing.Color.FromArgb(10, 255, 255, 255))
                                g.FillPath(glassBrush, gp2)
                            End Using
                            Using lightPen2 As New System.Drawing.Pen(System.Drawing.Color.FromArgb(55, 255, 255, 255), pThick2)
                                g.TranslateTransform(-pThick2, -pThick2)
                                g.DrawPath(lightPen2, gp2)
                                g.TranslateTransform(pThick2, pThick2)
                            End Using
                        End Using
                    End Using
                    g.ResetTransform()

                    ' ------------------------------------------------------------------
                    ' LỚP 3: THẺ GREEN CARD LOGO DIAGONAL GRADIENT
                    ' ------------------------------------------------------------------
                    Dim brandText As String = "WaterTreatment3D"
                    Dim contactText As String = "@tanphan1105 | Zalo: +84985267326"
                    Dim brandSize As Single = 2560.0F * 0.013F
                    Dim contactSize As Single = 2560.0F * 0.015F

                    Using brandFont As New System.Drawing.Font("Arial", brandSize, System.Drawing.FontStyle.Bold)
                    Using contactFont As New System.Drawing.Font("Arial", contactSize, System.Drawing.FontStyle.Bold)
                        Dim brandSz As System.Drawing.SizeF = g.MeasureString(brandText, brandFont)
                        Dim contactSz As System.Drawing.SizeF = g.MeasureString(contactText, contactFont)
                        Dim maxW As Single = Math.Max(brandSz.Width, contactSz.Width)
                        Dim qrSize As Single = 2560.0F * 0.075F
                        Dim cPad As Single = 2560.0F * 0.010F
                        Dim gap As Single = 2560.0F * 0.014F

                        ' LOAD QR CODE SAFE VIA MEMORYSTREAM
                        Dim hasQR As Boolean = False
                        Dim qrPath As String = masterDir & "\Z_Tools\wt3d_qr_green.png"
                        Dim qrBmp As System.Drawing.Bitmap = Nothing
                        If System.IO.File.Exists(qrPath) Then
                            Try
                                Dim qrBytes As Byte() = System.IO.File.ReadAllBytes(qrPath)
                                Dim qrMs As New System.IO.MemoryStream(qrBytes)
                                qrBmp = New System.Drawing.Bitmap(qrMs)
                                hasQR = True
                            Catch : End Try
                        End If

                        Dim effQRSize As Single = If(hasQR, qrSize, 0.0F)
                        Dim effGap As Single = If(hasQR, gap, 0.0F)

                        Dim totalW As Single = maxW + effGap + effQRSize
                        Dim textBlockH As Single = brandSz.Height + contactSz.Height + (1440.0F * 0.008F)
                        Dim totalH As Single = Math.Max(textBlockH, qrSize)

                        Dim cardX As Single = 2560.0F - totalW - (2560.0F * 0.025F) - cPad*2
                        Dim cardY As Single = 1440.0F - totalH - (1440.0F * 0.035F) - cPad*2

                        ' DRAW ROUNDED RECTANGLE GRADIENT CARD
                        Dim rectW As Single = totalW + cPad*2
                        Dim rectH As Single = totalH + cPad*2
                        Dim rRadius As Single = Math.Max(6.0F, 2560.0F * 0.008F)
                        Using cardPath As New System.Drawing.Drawing2D.GraphicsPath()
                            cardPath.AddArc(cardX, cardY, rRadius, rRadius, 180, 90)
                            cardPath.AddArc(cardX + rectW - rRadius, cardY, rRadius, rRadius, 270, 90)
                            cardPath.AddArc(cardX + rectW - rRadius, cardY + rectH - rRadius, rRadius, rRadius, 0, 90)
                            cardPath.AddArc(cardX, cardY + rectH - rRadius, rRadius, rRadius, 90, 90)
                            cardPath.CloseAllFigures()

                            Dim rectF As New System.Drawing.RectangleF(cardX, cardY, rectW, rectH)
                            Dim col1 As System.Drawing.Color = System.Drawing.Color.FromArgb(225, 52, 199, 89)
                            Dim col2 As System.Drawing.Color = System.Drawing.Color.FromArgb(220, 24, 150, 68)
                            Using gradBrush As New System.Drawing.Drawing2D.LinearGradientBrush(rectF, col1, col2, 45.0F)
                                g.FillPath(gradBrush, cardPath)
                            End Using
                            Using borderPen As New System.Drawing.Pen(System.Drawing.Color.FromArgb(240, 255, 255, 255), 1.0F)
                                g.DrawPath(borderPen, cardPath)
                            End Using
                        End Using

                        Dim currY As Single = cardY + cPad + (totalH - textBlockH) / 2.0F

                        ' DRAW BRAND TEXT & SHADOW
                        Using shadowBrush As New System.Drawing.SolidBrush(System.Drawing.Color.FromArgb(110, 10, 40, 15))
                            g.DrawString(brandText, brandFont, shadowBrush, cardX + cPad + 3, currY + 3)
                        End Using
                        Using mainBrush As New System.Drawing.SolidBrush(System.Drawing.Color.FromArgb(255, 255, 255, 255))
                            g.DrawString(brandText, brandFont, mainBrush, cardX + cPad, currY)
                        End Using

                        currY += brandSz.Height + (1440.0F * 0.004F)

                        ' DRAW CONTACT TEXT & SHADOW
                        Using shadowBrush As New System.Drawing.SolidBrush(System.Drawing.Color.FromArgb(110, 10, 40, 15))
                            g.DrawString(contactText, contactFont, shadowBrush, cardX + cPad + 3, currY + 3)
                        End Using
                        Using mainBrush As New System.Drawing.SolidBrush(System.Drawing.Color.FromArgb(255, 255, 255, 255))
                            g.DrawString(contactText, contactFont, mainBrush, cardX + cPad, currY)
                        End Using

                        If hasQR AndAlso qrBmp IsNot Nothing Then
                            Try
                                Dim qrX As Single = cardX + cPad + maxW + gap
                                Dim qrY As Single = cardY + cPad + (totalH - qrSize)/2.0F
                                Using qrBgPen As New System.Drawing.SolidBrush(System.Drawing.Color.FromArgb(255, 255, 255, 255))
                                    g.FillRectangle(qrBgPen, qrX - 4, qrY - 4, qrSize + 8, qrSize + 8)
                                End Using
                                g.DrawImage(qrBmp, qrX, qrY, qrSize, qrSize)
                                qrBmp.Dispose()
                            Catch : End Try
                        End If
                    End Using
                    End Using
                End Using
                wmkBmp.Save(wmkPath, System.Drawing.Imaging.ImageFormat.Png)
            End Using

            Dim ps1 As String = "d:\WT3D_Project\Z_Tools\Auto_Stitch_Video.ps1"
            If System.IO.File.Exists(ps1) Then
                Shell("powershell.exe -ExecutionPolicy Bypass -WindowStyle Hidden -File """ & ps1 & """ -TargetFolder """ & saveFolder & """", vbNormalFocus)
            End If
        Catch ex As Exception
            ' MessageBox.Show("Lỗi: " & ex.Message, "Error")
        End Try
    End Sub
End Class
