' ==============================================================================
' 03_STEP3_Batch_Render_Master.iLogicVb
' BƯỚC 3: Render Video Master 2K (16:9) & Video Shorts (9:16) cho Mô hình đang mở (hoặc Hàng loạt)
' ==============================================================================

AddReference "System.Windows.Forms"
AddReference "System.Private.Windows.Core"

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Try
            If ThisApplication.ActiveDocument IsNot Nothing Then
                ' Đang mở mô hình -> Render Video trực tiếp cho mô hình đang mở
                iLogicVb.Automation.RunExternalRule(ThisApplication.ActiveDocument, "d:\WT3D_Project\Z_Tools\CAM_0_RENDER_ALL.iLogicVb")
            Else
                ' Chưa mở file -> Kích hoạt bảng chọn file render video hàng loạt
                iLogicVb.Automation.RunExternalRule(Nothing, "d:\WT3D_Project\Z_Tools\Batch_Render_Master.iLogicVb")
            End If
        Catch ex As Exception
            MessageBox.Show("Lỗi thực thi Bước 3: " & ex.Message, "Báo Động Bước 3")
        End Try
    End Sub
End Class
