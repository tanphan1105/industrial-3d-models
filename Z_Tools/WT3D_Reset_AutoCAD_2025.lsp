(defun c:WT3D_RESET ()
  (vl-load-com)
  (mapcar '(lambda (x) (vl-catch-all-apply 'setvar x))
    '(("VTDURATION" 750)
      ("HPQUICKPREVIEW" 1)
      ("HPMAXAREAS" 100)
      ("SELECTIONCYCLING" 0)
      ("ROLLOVERTOOLTIPS" 1)
      ("SELECTIONEFFECT" 1)
      ("PRESELECTIONEFFECT" 1)
      ("LINESMOOTHING" 1)
      ("INPUTSEARCHDELAY" 500)
      ("DWGCHECK" 1)
      ("INDEXCTL" 0)
      ("XLOADCTL" 1)
      ("CACHEMAXFILES" 256)
      ("CACHEMAXTOTALSIZE" 1024)
      ("PALETTEOPAQUE" 0))
  )
  (princ "
🔄 [WT3D] ĐÃ KHÔI PHỤC TOÀN BỘ CÀI ĐẶT AUTOCAD 2025 VỀ MẶC ĐỊNH GỐC BAN ĐẦU!
")
  (princ)
)
(c:WT3D_RESET)
