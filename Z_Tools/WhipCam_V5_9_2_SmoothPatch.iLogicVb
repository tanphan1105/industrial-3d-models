AddReference "System.Drawing"
AddReference "System.Windows.Forms"

Imports System
Imports System.IO
Imports System.Collections.Generic
Imports System.Windows.Forms
Imports System.Drawing
Imports System.Drawing.Imaging
Imports System.Runtime.InteropServices
Imports System.Diagnostics
Imports Inventor

Public Class ThisRule

    ' ==========================================================================
    ' WT3D WHIPCAM STUDIO V5.9 - VIETNAMESE USER CONTROLS + DESIGN VIEW SAFE RENDER
    ' FAR-NEAR PULSED HERO ORBIT + C2 DISTANCE LAW + ANTI-FLIP CINEMATIC BANKING
    ' Lead Engineer: Phan Trong Tan (@tanphan1105) - WaterTreatment3D
    ' ==========================================================================

    <DllImport("user32.dll")> _
    Private Shared Function GetAsyncKeyState(ByVal vKey As Integer) As Short
    End Function

    Private Const VK_ESCAPE As Integer = &H1B

    Public Function CheckEscapeKey() As Boolean
        Return (GetAsyncKeyState(VK_ESCAPE) And &H8000) <> 0
    End Function

    ' --------------------------------------------------------------------------
    ' 1. 3D VECTOR MATH & RODRIGUES ROTATION
    ' --------------------------------------------------------------------------
    Public Class Vec3
        Public X As Double
        Public Y As Double
        Public Z As Double

        Public Sub New()
            X = 0.0 : Y = 0.0 : Z = 0.0
        End Sub

        Public Sub New(ByVal _x As Double, ByVal _y As Double, ByVal _z As Double)
            X = _x : Y = _y : Z = _z
        End Sub

        Public Shared Operator +(ByVal a As Vec3, ByVal b As Vec3) As Vec3
            Return New Vec3(a.X + b.X, a.Y + b.Y, a.Z + b.Z)
        End Operator

        Public Shared Operator -(ByVal a As Vec3, ByVal b As Vec3) As Vec3
            Return New Vec3(a.X - b.X, a.Y - b.Y, a.Z - b.Z)
        End Operator

        Public Shared Operator -(ByVal a As Vec3) As Vec3
            Return New Vec3(-a.X, -a.Y, -a.Z)
        End Operator

        Public Shared Operator *(ByVal s As Double, ByVal a As Vec3) As Vec3
            Return New Vec3(s * a.X, s * a.Y, s * a.Z)
        End Operator

        Public Shared Operator *(ByVal a As Vec3, ByVal s As Double) As Vec3
            Return New Vec3(s * a.X, s * a.Y, s * a.Z)
        End Operator

        Public Shared Operator /(ByVal a As Vec3, ByVal s As Double) As Vec3
            If Math.Abs(s) < 1E-12 Then Return New Vec3(0, 0, 0)
            Return New Vec3(a.X / s, a.Y / s, a.Z / s)
        End Operator

        Public Function Dot(ByVal b As Vec3) As Double
            Return X * b.X + Y * b.Y + Z * b.Z
        End Function

        Public Function Cross(ByVal b As Vec3) As Vec3
            Return New Vec3(Y * b.Z - Z * b.Y, Z * b.X - X * b.Z, X * b.Y - Y * b.X)
        End Function

        Public Function Length() As Double
            Return Math.Sqrt(X * X + Y * Y + Z * Z)
        End Function

        Public Function Normalize() As Vec3
            Dim l As Double = Length()
            If l < 1E-12 Then Return New Vec3(0, 1, 0) ' Default to Y-up
            Return New Vec3(X / l, Y / l, Z / l)
        End Function

        Public Shared Function Lerp(ByVal a As Vec3, ByVal b As Vec3, ByVal t As Double) As Vec3
            Return a + t * (b - a)
        End Function

        Public Shared Function Distance(ByVal a As Vec3, ByVal b As Vec3) As Double
            Return (a - b).Length()
        End Function

        Public Shared Function RodriguesRotate(ByVal v As Vec3, ByVal axis As Vec3, ByVal angleRad As Double) As Vec3
            Dim k As Vec3 = axis.Normalize()
            Dim cosA As Double = Math.Cos(angleRad)
            Dim sinA As Double = Math.Sin(angleRad)
            Return v * cosA + k.Cross(v) * sinA + k * (k.Dot(v)) * (1.0 - cosA)
        End Function
    End Class

    ' --------------------------------------------------------------------------
    ' 2. CAMERA STATE & METADATA
    ' --------------------------------------------------------------------------
    Public Class CameraState
        Public Eye As Vec3
        Public Target As Vec3
        Public UpVector As Vec3
        Public FOV As Double
        Public RollDeg As Double
        Public Speed As Double
        Public Accel As Double
        Public Jerk As Double
        Public ActiveHeroName As String

        Public Sub New()
            Eye = New Vec3() : Target = New Vec3() : UpVector = New Vec3(0, 1, 0) ' True Y-up default
            FOV = 50.0 : RollDeg = 0.0 : Speed = 0.0 : Accel = 0.0 : Jerk = 0.0
            ActiveHeroName = "Overview"
        End Sub
    End Class

    Public Class HeroTarget
        Public Occurrence As ComponentOccurrence
        Public Name As String
        Public Center As Vec3
        Public MinPt As Vec3
        Public MaxPt As Vec3
        Public SizeU As Double
        Public SizeV As Double
        Public SizeW As Double
        Public AdaptiveClearance As Double
    End Class

    Public Class ModelInfo
        Public Center As Vec3
        Public U As Vec3
        Public V As Vec3
        Public W As Vec3
        Public RU As Double
        Public RV As Double
        Public RH As Double
    End Class

    Public Class CameraSettings
        ' --- Output / timeline ---
        Public DurationSeconds As Double = 10.5
        Public FPS As Integer = 30
        Public Width As Integer = 1080
        Public Height As Integer = 1920
        Public TotalFrames As Integer = 315
        Public RunMode As String = "PREVIEW"

        ' --- User-facing cinematic controls ---
        Public FarDistanceScale As Double = 2.65       ' Normal orbit radius / Hero base radius
        Public Near1DistanceScale As Double = 1.05     ' First push-in target radius
        Public Near2DistanceScale As Double = 0.62     ' Second / strongest push-in target radius
        Public ReleaseDistanceBoost As Double = 0.30   ' Extra pull-out between close passes
        Public OrbitSweepDegrees As Double = 190.0     ' Total circular sweep per Hero
        Public OrbitOrganicBiasDegrees As Double = 5.0 ' Gentle arc bias, not vibration

        Public FastSpeedMultiplier As Double = 1.55     ' >1 = faster dive / escape
        Public NearHoldMultiplier As Double = 1.50      ' >1 = longer slow inspection
        Public NearHoldSpeedPercent As Double = 9.0   ' Lower = closer to a stop at Hero

        Public FOVFarDegrees As Double = 48.0
        Public FOVFastDegrees As Double = 62.0
        Public FOVNearDegrees As Double = 70.0
        Public FOVRevealDegrees As Double = 47.0

        Public MaxBankDegrees As Double = 8.5
        Public BankGainMultiplier As Double = 1.10

        Public EnableMotionBlur As Boolean = True
        Public ShutterAngle As Double = 180.0

        ' --- Render safety / visibility ---
        ' Always keep the video consistent with the current Inventor assembly view:
        ' hidden occurrences stay hidden; construction geometry is suppressed only
        ' during preview/export and restored afterwards.
        Public PreserveCurrentOccurrenceVisibility As Boolean = True
        Public HideConstructionGeometryDuringRender As Boolean = True
        Public CaptureFromActiveView As Boolean = True
    End Class

    ' --------------------------------------------------------------------------
    ' 3. QUINTIC HERMITE SPLINE (C2 CONTINUITY)
    ' --------------------------------------------------------------------------
    Public Class QuinticHermiteSpline
        Public Shared Function Evaluate(ByVal P0 As Vec3, ByVal V0 As Vec3, ByVal A0 As Vec3, _
                                        ByVal P1 As Vec3, ByVal V1 As Vec3, ByVal A1 As Vec3, ByVal u As Double) As Vec3
            Dim t As Double = Math.Max(0.0, Math.Min(1.0, u))
            Dim t2 As Double = t * t
            Dim t3 As Double = t2 * t
            Dim t4 As Double = t3 * t
            Dim t5 As Double = t4 * t

            Dim h0 As Double = 1.0 - 10.0 * t3 + 15.0 * t4 - 6.0 * t5
            Dim h1 As Double = t - 6.0 * t3 + 8.0 * t4 - 3.0 * t5
            Dim h2 As Double = 0.5 * t2 - 1.5 * t3 + 1.5 * t4 - 0.5 * t5
            Dim h3 As Double = 0.5 * t3 - t4 + 0.5 * t5
            Dim h4 As Double = -4.0 * t3 + 7.0 * t4 - 3.0 * t5
            Dim h5 As Double = 10.0 * t3 - 15.0 * t4 + 6.0 * t5

            Return h0 * P0 + h1 * V0 + h2 * A0 + h3 * A1 + h4 * V1 + h5 * P1
        End Function

        Public Shared Function EvaluateDeriv(ByVal P0 As Vec3, ByVal V0 As Vec3, ByVal A0 As Vec3, _
                                             ByVal P1 As Vec3, ByVal V1 As Vec3, ByVal A1 As Vec3, ByVal u As Double) As Vec3
            Dim t As Double = Math.Max(0.0, Math.Min(1.0, u))
            Dim t2 As Double = t * t
            Dim t3 As Double = t2 * t
            Dim t4 As Double = t3 * t

            Dim dh0 As Double = -30.0 * t2 + 60.0 * t3 - 30.0 * t4
            Dim dh1 As Double = 1.0 - 18.0 * t2 + 32.0 * t3 - 15.0 * t4
            Dim dh2 As Double = t - 4.5 * t2 + 6.0 * t3 - 2.5 * t4
            Dim dh3 As Double = 1.5 * t2 - 4.0 * t3 + 2.5 * t4
            Dim dh4 As Double = -12.0 * t2 + 28.0 * t3 - 15.0 * t4
            Dim dh5 As Double = 30.0 * t2 - 60.0 * t3 + 30.0 * t4

            Return dh0 * P0 + dh1 * V0 + dh2 * A0 + dh3 * A1 + dh4 * V1 + dh5 * P1
        End Function

        Public Shared Function EvaluateSecondDeriv(ByVal P0 As Vec3, ByVal V0 As Vec3, ByVal A0 As Vec3, _
                                                   ByVal P1 As Vec3, ByVal V1 As Vec3, ByVal A1 As Vec3, ByVal u As Double) As Vec3
            Dim t As Double = Math.Max(0.0, Math.Min(1.0, u))
            Dim t2 As Double = t * t
            Dim t3 As Double = t2 * t

            Dim d2h0 As Double = -60.0 * t + 180.0 * t2 - 120.0 * t3
            Dim d2h1 As Double = -36.0 * t + 96.0 * t2 - 60.0 * t3
            Dim d2h2 As Double = 1.0 - 9.0 * t + 18.0 * t2 - 10.0 * t3
            Dim d2h3 As Double = 3.0 * t - 12.0 * t2 + 10.0 * t3
            Dim d2h4 As Double = -24.0 * t + 84.0 * t2 - 60.0 * t3
            Dim d2h5 As Double = 60.0 * t - 180.0 * t2 + 120.0 * t3

            Return d2h0 * P0 + d2h1 * V0 + d2h2 * A0 + d2h3 * A1 + d2h4 * V1 + d2h5 * P1
        End Function
    End Class

    ' --------------------------------------------------------------------------
    ' 4. MASTER SPATIAL RAIL (CONTINUOUS 3D CURVE + ARC-LENGTH LUT)
    ' --------------------------------------------------------------------------
    Public Class MasterSpatialRail
        Public Waypoints As New List(Of Vec3)()
        Public Tangents As New List(Of Vec3)()
        Public Accels As New List(Of Vec3)()
        Public NumSegments As Integer

        Private Const LUT_SIZE As Integer = 2000
        Private CumDist(2000) As Double
        Private NormDistLUT(2000) As Double
        Private USamples(2000) As Double
        Public TotalRailLength As Double

        Private Function HorizontalOutward(ByVal p As Vec3, ByVal center As Vec3, ByVal worldUp As Vec3, ByVal fallback As Vec3) As Vec3
            Dim d As Vec3 = p - center
            d = d - worldUp * d.Dot(worldUp)
            If d.Length() < 1E-6 Then Return fallback.Normalize()
            Return d.Normalize()
        End Function

        Private Function HeroOrbitPoint(ByVal ht As HeroTarget, _
                                        ByVal model As ModelInfo, _
                                        ByVal radial As Vec3, _
                                        ByVal tangent As Vec3, _
                                        ByVal q As Double, _
                                        ByVal directionSign As Double, _
                                        ByVal orbitStrength As Double, _
                                        ByVal settings As CameraSettings) As Vec3
            q = Math.Max(0.0, Math.Min(1.0, q))

            Dim localSize As Double = Math.Max(20.0, Math.Max(ht.SizeU, Math.Max(ht.SizeV, ht.SizeW)))
            Dim clearance As Double = ht.AdaptiveClearance
            If clearance <= 0.0 Then clearance = Math.Max(10.0, Math.Min(30.0, localSize * 0.14))
            clearance = Math.Max(8.0, Math.Min(32.0, clearance))

            ' Base orbit radius follows the REAL Hero size, not the whole skid.
            Dim baseRadius As Double = clearance + Math.Max(16.0, localSize * 0.30)

            ' V5.5 RHYTHM ORBIT: prioritize a clean circular arc inside each Hero shot.
            ' Direction alternates between Heroes (+/- directionSign), which preserves the
            ' left-right cinematic reversal without injecting rapid curvature sign changes
            ' inside one shot. A gentle single-wave bias keeps the path organic.
            Dim sweepDeg As Double = Math.Max(40.0, Math.Min(320.0, settings.OrbitSweepDegrees))
            Dim organicDeg As Double = Math.Max(0.0, Math.Min(45.0, settings.OrbitOrganicBiasDegrees))
            ' V5.10 ORGANIC BOUNDARY FADE: triệt sine wave tại q=0 và q=1 (chống kink)
            Dim fadeQ As Double = Math.Max(0.0, Math.Min(1.0, q / 0.12)) * Math.Max(0.0, Math.Min(1.0, (1.0 - q) / 0.12))
            Dim organicEffective As Double = organicDeg * fadeQ * fadeQ * (3.0 - 2.0 * fadeQ)
            Dim thetaDeg As Double = directionSign * ((-0.5 * sweepDeg + sweepDeg * q) + _
                                                       (organicEffective * orbitStrength) * Math.Sin(2.0 * Math.PI * q))
            Dim theta As Double = thetaDeg * Math.PI / 180.0

            ' V5.5 DISTANCE PULSE: the reference repeatedly goes FAR -> NEAR -> RELEASE
            ' -> NEAR HARDER -> ESCAPE. Two Gaussian close-pass pulses create that
            ' deliberate "nhan nha" instead of one generic mid-shot zoom.
            ' Narrow pulse widths keep most of the shot visibly farther away.
            Dim pulse1 As Double = Math.Exp(-Math.Pow((q - 0.22) / 0.075, 2.0))
            Dim pulse2 As Double = Math.Exp(-Math.Pow((q - 0.72) / 0.065, 2.0))
            Dim releaseBell As Double = Math.Exp(-Math.Pow((q - 0.48) / 0.10, 2.0))

            ' V5.5: FAR is the default state. Near passes are intentionally brief.
            ' First push-in is moderate; second push-in is deeper and shorter.
            Dim farScale As Double = Math.Max(0.8, Math.Min(5.0, settings.FarDistanceScale))
            Dim near1Scale As Double = Math.Max(0.35, Math.Min(farScale, settings.Near1DistanceScale))
            Dim near2Scale As Double = Math.Max(0.30, Math.Min(farScale, settings.Near2DistanceScale))
            Dim releaseBoost As Double = Math.Max(0.0, Math.Min(1.5, settings.ReleaseDistanceBoost))

            ' User-controlled distance rhythm. Most of the shot stays at FarDistanceScale.
            ' Only the two narrow Gaussian windows dive toward Near1 / Near2.
            Dim radiusScale As Double = farScale _
                                      + (near1Scale - farScale) * pulse1 _
                                      + (near2Scale - farScale) * pulse2 _
                                      + releaseBoost * releaseBell
            ' No high-frequency radius breathing: the strong FAR/NEAR pulses already
            ' provide the cinematic emphasis, and extra oscillation can read as vibration.
            radiusScale = Math.Max(0.30, radiusScale)

            ' Elliptical orbit exaggerates foreground parallax during both close pulses.
            Dim rRadial As Double = baseRadius * radiusScale
            Dim rTangent As Double = rRadial * (1.12 + 0.11 * orbitStrength)

            ' Rise/fall is phase shifted. Close passes also dive slightly, especially
            ' the second pulse, producing the far-high -> near-low -> reveal rhythm.
            Dim baseLift As Double = Math.Max(4.0, Math.Min(18.0, ht.SizeW * 0.10 + model.RH * 0.045))
            Dim lift As Double = baseLift + (0.10 * model.RH * orbitStrength) * Math.Sin(2.0 * Math.PI * q + 0.65)
            lift += (0.030 * model.RH) * Math.Sin(4.0 * Math.PI * q) * Math.Max(0.0, Math.Sin(Math.PI * q))  ' V5.10: fade lift oscillation at boundaries
            lift -= (0.055 * model.RH) * pulse1
            lift -= (0.090 * model.RH) * pulse2

            Return ht.Center + radial * (Math.Cos(theta) * rRadial) + tangent * (Math.Sin(theta) * rTangent) + model.W * lift
        End Function

        Private Sub AddHeroOscillatingOrbitPass(ByVal ht As HeroTarget, _
                                                 ByVal model As ModelInfo, _
                                                 ByVal directionSign As Double, _
                                                 ByVal orbitStrength As Double, _
                                                 ByVal settings As CameraSettings)
            Dim W As Vec3 = model.W
            Dim fallback As Vec3 = If(directionSign >= 0.0, -model.V, model.V)
            Dim radial As Vec3 = HorizontalOutward(ht.Center, model.Center, W, fallback)
            Dim tangent As Vec3 = W.Cross(radial).Normalize()

            ' Seventeen samples preserve narrow near-pass windows while keeping the far shell dominant
            ' while the quintic master rail keeps the result rounded and smooth.
            Dim samples As Integer = 17
            For i As Integer = 0 To samples - 1
                Dim q As Double = CDbl(i) / CDbl(samples - 1)
                Waypoints.Add(HeroOrbitPoint(ht, model, radial, tangent, q, directionSign, orbitStrength, settings))
            Next
        End Sub

        Public Sub BuildRail(ByVal model As ModelInfo, ByVal heroes As List(Of HeroTarget), ByVal settings As CameraSettings)
            Waypoints.Clear()
            Tangents.Clear()
            Accels.Clear()

            Dim U As Vec3 = model.U
            Dim V As Vec3 = model.V
            Dim W As Vec3 = model.W
            Dim C As Vec3 = model.Center

            Dim RU As Double = Math.Max(25.0, model.RU)
            Dim RV As Double = Math.Max(25.0, model.RV)
            Dim RH As Double = Math.Max(30.0, model.RH)

            ' ------------------------------------------------------------------
            ' V5.5 RHYTHM ORBIT – FAST/SLOW HERO PULSES
            ' The reference does NOT just fly Entry -> Apex -> Exit.
            ' Around each real Hero the camera sweeps in a rounded orbit, reverses
            ' direction smoothly, pulses FAR->NEAR->FAR->NEAR HARDER, then escapes.
            ' This preserves the appealing "bay tron, dao toi dao lui" behavior
            ' while the orientation system separately prevents unwanted horizon flips.
            ' ------------------------------------------------------------------
            Waypoints.Add(C - 1.90 * RU * U - 2.05 * RV * V + 1.15 * RH * W)

            If heroes IsNot Nothing AndAlso heroes.Count >= 4 Then
                AddHeroOscillatingOrbitPass(heroes(0), model, +1.0, 0.90, settings) ' Pump: rounded L-R-L orbit
                AddHeroOscillatingOrbitPass(heroes(1), model, -1.0, 1.05, settings) ' Membrane: reverse phase, stronger
                AddHeroOscillatingOrbitPass(heroes(2), model, +1.0, 1.15, settings) ' Panel: strongest whip/orbit reversal
                AddHeroOscillatingOrbitPass(heroes(3), model, -1.0, 0.95, settings) ' UV/manifold: opposite closing sweep
            Else
                ' Fallback still uses rounded S-orbit behavior around the skid center.
                For i As Integer = 0 To 20
                    Dim q As Double = CDbl(i) / 20.0
                    Dim sweep As Double = Math.Max(40.0, Math.Min(320.0, settings.OrbitSweepDegrees))
                    Dim theta As Double = ((-0.5 * sweep + sweep * q) + settings.OrbitOrganicBiasDegrees * Math.Sin(2.0 * Math.PI * q)) * Math.PI / 180.0
                    Dim fallbackFar As Double = Math.Max(1.0, settings.FarDistanceScale)
                    Dim radiusU As Double = RU * fallbackFar * (1.0 - 0.16 * Math.Pow(Math.Sin(Math.PI * q), 2.0))
                    Dim radiusV As Double = RV * fallbackFar * (1.03 - 0.14 * Math.Pow(Math.Sin(Math.PI * q), 2.0))
                    Dim lift As Double = (0.55 + 0.16 * Math.Sin(2.0 * Math.PI * q + 0.6)) * RH
                    Waypoints.Add(C + U * (Math.Cos(theta) * radiusU) + V * (Math.Sin(theta) * radiusV) + W * lift)
                Next
            End If

            ' Curved asymmetric escape, not an orthographic final view.
            Waypoints.Add(C - 2.15 * RU * U - 1.65 * RV * V + 1.65 * RH * W)

            NumSegments = Waypoints.Count - 1

            For i As Integer = 0 To Waypoints.Count - 1
                Tangents.Add(New Vec3())
                Accels.Add(New Vec3())
            Next

            ' C2-friendly derivative estimates. Tangents are deliberately strong enough
            ' to keep the camera sweeping through each Apex instead of "point-to-point" motion.
            For i As Integer = 1 To NumSegments - 1
                Tangents(i) = 0.46 * (Waypoints(i + 1) - Waypoints(i - 1))
                Accels(i) = 0.46 * (Waypoints(i + 1) - 2.0 * Waypoints(i) + Waypoints(i - 1))
            Next

            Tangents(0) = (Waypoints(1) - Waypoints(0)) * 0.72
            Accels(0) = New Vec3(0, 0, 0)
            Tangents(NumSegments) = (Waypoints(NumSegments) - Waypoints(NumSegments - 1)) * 0.72
            Accels(NumSegments) = New Vec3(0, 0, 0)

            CumDist(0) = 0.0
            USamples(0) = 0.0
            NormDistLUT(0) = 0.0

            Dim prevPt As Vec3 = EvaluateRailDirect(0.0)

            For k As Integer = 1 To LUT_SIZE
                Dim uVal As Double = CDbl(k) / CDbl(LUT_SIZE) * CDbl(NumSegments)
                USamples(k) = uVal
                Dim currPt As Vec3 = EvaluateRailDirect(uVal)
                Dim chord As Double = (currPt - prevPt).Length()
                CumDist(k) = CumDist(k - 1) + chord
                prevPt = currPt
            Next

            TotalRailLength = Math.Max(1E-9, CumDist(LUT_SIZE))
            For k As Integer = 0 To LUT_SIZE
                NormDistLUT(k) = CumDist(k) / TotalRailLength
            Next
        End Sub

        Private Function EvaluateRailDirect(ByVal uGlobal As Double) As Vec3
            uGlobal = Math.Max(0.0, Math.Min(CDbl(NumSegments), uGlobal))
            Dim seg As Integer = CInt(Math.Floor(uGlobal))
            Dim uLocal As Double = uGlobal - seg
            If seg >= NumSegments Then
                seg = NumSegments - 1
                uLocal = 1.0
            End If

            Return QuinticHermiteSpline.Evaluate(Waypoints(seg), Tangents(seg), Accels(seg), _
                                                 Waypoints(seg + 1), Tangents(seg + 1), Accels(seg + 1), uLocal)
        End Function

        Public Function GetNormalizedDistanceAtU(ByVal uGlobal As Double) As Double
            uGlobal = Math.Max(0.0, Math.Min(CDbl(NumSegments), uGlobal))
            If NumSegments <= 0 Then Return 0.0

            Dim x As Double = (uGlobal / CDbl(NumSegments)) * CDbl(LUT_SIZE)
            Dim i0 As Integer = CInt(Math.Floor(x))
            If i0 >= LUT_SIZE Then Return 1.0
            Dim a As Double = x - CDbl(i0)
            Return NormDistLUT(i0) * (1.0 - a) + NormDistLUT(i0 + 1) * a
        End Function

        Public Function InverseArcLength(ByVal sNorm As Double) As Double
            sNorm = Math.Max(0.0, Math.Min(1.0, sNorm))

            Dim low As Integer = 0
            Dim high As Integer = LUT_SIZE

            While low < high
                Dim mid As Integer = (low + high) \ 2
                If NormDistLUT(mid) < sNorm Then
                    low = mid + 1
                Else
                    high = mid
                End If
            End While

            Dim idx As Integer = Math.Max(0, Math.Min(LUT_SIZE - 1, low - 1))
            Dim ds As Double = NormDistLUT(idx + 1) - NormDistLUT(idx)
            If ds < 1E-12 Then Return USamples(idx)

            Dim alpha As Double = (sNorm - NormDistLUT(idx)) / ds
            Return USamples(idx) + alpha * (USamples(idx + 1) - USamples(idx))
        End Function

        Public Sub EvaluateRailAtDistance(ByVal sNorm As Double, ByRef outPos As Vec3, ByRef outTangent As Vec3, ByRef outSecDeriv As Vec3)
            Dim uGlobal As Double = InverseArcLength(sNorm)
            uGlobal = Math.Max(0.0, Math.Min(CDbl(NumSegments), uGlobal))
            Dim seg As Integer = CInt(Math.Floor(uGlobal))
            Dim uLocal As Double = uGlobal - seg
            If seg >= NumSegments Then
                seg = NumSegments - 1
                uLocal = 1.0
            End If

            outPos = QuinticHermiteSpline.Evaluate(Waypoints(seg), Tangents(seg), Accels(seg), _
                                                   Waypoints(seg + 1), Tangents(seg + 1), Accels(seg + 1), uLocal)
            outTangent = QuinticHermiteSpline.EvaluateDeriv(Waypoints(seg), Tangents(seg), Accels(seg), _
                                                           Waypoints(seg + 1), Tangents(seg + 1), Accels(seg + 1), uLocal)
            outSecDeriv = QuinticHermiteSpline.EvaluateSecondDeriv(Waypoints(seg), Tangents(seg), Accels(seg), _
                                                                 Waypoints(seg + 1), Tangents(seg + 1), Accels(seg + 1), uLocal)
        End Sub
    End Class

    ' --------------------------------------------------------------------------
    ' 5. JERK-LIMITED SPEED LAW (PCHIP MONOTONIC CUBIC HERMITE)
    ' --------------------------------------------------------------------------
    Public Class JerkLimitedSpeedLaw
        ' V5.5 RHYTHM-LOCKED SPEED LAW.
        ' Timing is tied to the actual Hero-orbit geometry instead of generic global s keys:
        ' FAR -> FAST PUSH-IN -> SLOW/HOLD NEAR -> FAST CIRCULAR SWEEP OUT/IN
        ' -> SLOW/HOLD NEAR -> FAST ESCAPE -> next Hero.
        Private T_keys As Double()
        Private S_keys As Double()
        Private V_keys As Double()
        Public TotalDuration As Double = 10.5

        Public Sub Initialize(ByVal targetDuration As Double, ByVal rail As MasterSpatialRail, ByVal settings As CameraSettings)
            TotalDuration = Math.Max(1.0, targetDuration)

            ' Four Hero passes, 17 waypoints each, preceded by one overview waypoint.
            ' Fractional u values target the REAL near-pulse centers q=0.22/0.72 and
            ' very short q windows after them for the visual "pause to inspect".
            Dim uList As New List(Of Double)()
            uList.Add(0.0)

            If rail.Waypoints.Count >= 70 Then
                For heroIndex As Integer = 0 To 3
                    Dim heroStart As Double = 1.0 + 17.0 * CDbl(heroIndex)
                    uList.Add(heroStart + 16.0 * 0.22) ' close pulse 1
                    uList.Add(heroStart + 16.0 * 0.25) ' short slow inspection window
                    uList.Add(heroStart + 16.0 * 0.72) ' close pulse 2
                    uList.Add(heroStart + 16.0 * 0.75) ' short slow inspection window
                Next
                uList.Add(CDbl(rail.NumSegments))
            Else
                ' Safe fallback for unexpected geometry.
                For i As Integer = 1 To 8
                    uList.Add(CDbl(rail.NumSegments) * CDbl(i) / 9.0)
                Next
                uList.Add(CDbl(rail.NumSegments))
            End If

            Dim n As Integer = uList.Count
            ReDim T_keys(n - 1)
            ReDim S_keys(n - 1)
            ReDim V_keys(n - 1)

            For i As Integer = 0 To n - 1
                S_keys(i) = rail.GetNormalizedDistanceAtU(uList(i))
            Next

            ' Editorial durations for the normal four-Hero rail.
            ' FAST segments create the dive/escape. HOLD segments are long in time but
            ' tiny in rail distance, so the camera almost stops while still drifting.
            Dim segDur As Double()
            Dim fastMul As Double = Math.Max(0.35, Math.Min(4.0, settings.FastSpeedMultiplier))
            Dim holdMul As Double = Math.Max(0.25, Math.Min(4.0, settings.NearHoldMultiplier))
            If n = 18 Then
                ReDim segDur(n - 2)
                For i As Integer = 0 To n - 2
                    If i = n - 2 Then
                        segDur(i) = 0.75 / fastMul ' final fast escape
                    Else
                        Dim phase As Integer = i Mod 4
                        Select Case phase
                            Case 0
                                segDur(i) = If(i = 0, 0.55, 0.70) / fastMul ' far -> near dive
                            Case 1
                                segDur(i) = 0.50 * holdMul                ' near hold 1
                            Case 2
                                segDur(i) = 0.70 / fastMul                ' fast circular sweep / push
                            Case Else
                                segDur(i) = 0.55 * holdMul                ' near hold 2
                        End Select
                    End If
                Next
            Else
                ReDim segDur(n - 2)
                For i As Integer = 0 To n - 2
                    segDur(i) = 1.0
                Next
            End If

            Dim rawTotal As Double = 0.0
            For i As Integer = 0 To segDur.Length - 1
                rawTotal += segDur(i)
            Next
            Dim timeScale As Double = TotalDuration / Math.Max(1E-9, rawTotal)

            T_keys(0) = 0.0
            For i As Integer = 0 To n - 2
                T_keys(i + 1) = T_keys(i) + segDur(i) * timeScale
            Next
            T_keys(n - 1) = TotalDuration

            ' Low endpoint velocity at every near key. Fast segments accelerate strongly
            ' in the middle and brake naturally into the close inspection moment.
            Dim segmentDt(n - 2) As Double
            Dim delta(n - 2) As Double
            For i As Integer = 0 To n - 2
                segmentDt(i) = Math.Max(1E-9, T_keys(i + 1) - T_keys(i))
                delta(i) = (S_keys(i + 1) - S_keys(i)) / segmentDt(i)
            Next

            Dim holdSpeedFrac As Double = Math.Max(0.0, Math.Min(0.60, settings.NearHoldSpeedPercent / 100.0))
            V_keys(0) = Math.Max(0.0, delta(0) * holdSpeedFrac)
            V_keys(n - 1) = Math.Max(0.0, delta(n - 2) * holdSpeedFrac)

            For i As Integer = 1 To n - 2
                Dim localMin As Double = Math.Min(Math.Max(0.0, delta(i - 1)), Math.Max(0.0, delta(i)))
                V_keys(i) = localMin * holdSpeedFrac
            Next
        End Sub

        Private Function FindSegment(ByVal t As Double) As Integer
            Dim n As Integer = T_keys.Length
            If t <= T_keys(0) Then Return 0
            If t >= T_keys(n - 1) Then Return n - 2
            Dim idx As Integer = 0
            While idx < n - 2 AndAlso T_keys(idx + 1) < t
                idx += 1
            End While
            Return idx
        End Function

        Private Sub EvalSegment(ByVal idx As Integer, ByVal t As Double, ByRef sOut As Double, ByRef dsdtOut As Double, ByRef d2sdt2Out As Double)
            Dim t0 As Double = T_keys(idx)
            Dim t1 As Double = T_keys(idx + 1)
            Dim h As Double = Math.Max(1E-9, t1 - t0)
            Dim u As Double = Math.Max(0.0, Math.Min(1.0, (t - t0) / h))

            Dim u2 As Double = u * u
            Dim u3 As Double = u2 * u
            Dim u4 As Double = u3 * u
            Dim u5 As Double = u4 * u

            Dim h0 As Double = 1.0 - 10.0 * u3 + 15.0 * u4 - 6.0 * u5
            Dim h1 As Double = u - 6.0 * u3 + 8.0 * u4 - 3.0 * u5
            Dim h4 As Double = -4.0 * u3 + 7.0 * u4 - 3.0 * u5
            Dim h5 As Double = 10.0 * u3 - 15.0 * u4 + 6.0 * u5

            Dim dh0 As Double = -30.0 * u2 + 60.0 * u3 - 30.0 * u4
            Dim dh1 As Double = 1.0 - 18.0 * u2 + 32.0 * u3 - 15.0 * u4
            Dim dh4 As Double = -12.0 * u2 + 28.0 * u3 - 15.0 * u4
            Dim dh5 As Double = 30.0 * u2 - 60.0 * u3 + 30.0 * u4

            Dim d2h0 As Double = -60.0 * u + 180.0 * u2 - 120.0 * u3
            Dim d2h1 As Double = -36.0 * u + 96.0 * u2 - 60.0 * u3
            Dim d2h4 As Double = -24.0 * u + 84.0 * u2 - 60.0 * u3
            Dim d2h5 As Double = 60.0 * u - 180.0 * u2 + 120.0 * u3

            ' Zero acceleration boundary conditions at editorial keys => C2 time law.
            Dim v0u As Double = V_keys(idx) * h
            Dim v1u As Double = V_keys(idx + 1) * h

            sOut = h0 * S_keys(idx) + h1 * v0u + h4 * v1u + h5 * S_keys(idx + 1)
            Dim dsdu As Double = dh0 * S_keys(idx) + dh1 * v0u + dh4 * v1u + dh5 * S_keys(idx + 1)
            Dim d2sdu2 As Double = d2h0 * S_keys(idx) + d2h1 * v0u + d2h4 * v1u + d2h5 * S_keys(idx + 1)

            dsdtOut = dsdu / h
            d2sdt2Out = d2sdu2 / (h * h)
        End Sub

        Public Function GetNormalizedDistance(ByVal t As Double) As Double
            t = Math.Max(0.0, Math.Min(TotalDuration, t))
            Dim sVal As Double = 0.0, vVal As Double = 0.0, aVal As Double = 0.0
            EvalSegment(FindSegment(t), t, sVal, vVal, aVal)
            Return Math.Max(0.0, Math.Min(1.0, sVal))
        End Function

        Public Function EvaluateSpeed(ByVal t As Double) As Double
            t = Math.Max(0.0, Math.Min(TotalDuration, t))
            Dim sVal As Double = 0.0, vVal As Double = 0.0, aVal As Double = 0.0
            EvalSegment(FindSegment(t), t, sVal, vVal, aVal)
            Return Math.Max(0.0, vVal * 1000.0) ' Cinematic intensity units for telemetry/blur
        End Function

        Public Function EvaluateAcceleration(ByVal t As Double) As Double
            t = Math.Max(0.0, Math.Min(TotalDuration, t))
            Dim sVal As Double = 0.0, vVal As Double = 0.0, aVal As Double = 0.0
            EvalSegment(FindSegment(t), t, sVal, vVal, aVal)
            Return aVal * 1000.0
        End Function
    End Class

    ' --------------------------------------------------------------------------
    ' 6. ANTI-FLIP CINEMATIC ORIENTATION
    '    Deterministic spatially-smoothed banking for preview/export consistency.
    ' --------------------------------------------------------------------------
    Public Class ParallelTransportOrientation
        Private LastBankDeg As Double = 0.0

        Public Sub Reset()
            LastBankDeg = 0.0
        End Sub

        Public Shared Function SignedTurnSignal(ByVal railTangent As Vec3, _
                                                ByVal railSecondDeriv As Vec3, _
                                                ByVal worldUp As Vec3) As Double
            Dim tLen As Double = Math.Max(1E-9, railTangent.Length())
            Dim aLen As Double = Math.Max(1E-9, railSecondDeriv.Length())
            Dim sig As Double = railTangent.Cross(railSecondDeriv).Dot(worldUp) / (tLen * aLen)
            Return Math.Max(-1.0, Math.Min(1.0, sig))
        End Function

        Private Shared Function SmoothStep01(ByVal x As Double) As Double
            x = Math.Max(0.0, Math.Min(1.0, x))
            Return x * x * (3.0 - 2.0 * x)
        End Function

        Public Function EvaluateOrientation(ByVal F_curr As Vec3, _
                                            ByVal worldUp As Vec3, _
                                            ByVal smoothedTurnSignal As Double, _
                                            ByVal speedIntent As Double, _
                                            ByVal bankGain As Double, _
                                            ByVal maxBankUser As Double) As Vec3
            F_curr = F_curr.Normalize()

            ' Robust level frame. Normal skid flights are nearly horizontal; this fallback
            ' prevents an UpVector inversion if Forward temporarily approaches WorldUp.
            Dim R_level As Vec3 = F_curr.Cross(worldUp)
            If R_level.Length() < 1E-6 Then R_level = New Vec3(1, 0, 0)
            R_level = R_level.Normalize()
            Dim U_level As Vec3 = R_level.Cross(F_curr).Normalize()

            ' Anti-flip deadband around an inflection point. Tiny curvature sign changes
            ' must NOT immediately reverse the camera bank.
            Dim deadband As Double = 0.12
            Dim absTurn As Double = Math.Abs(smoothedTurnSignal)
            Dim turnStrength As Double = 0.0
            If absTurn > deadband Then
                turnStrength = (absTurn - deadband) / (1.0 - deadband)
                turnStrength = SmoothStep01(turnStrength)
            End If

            Dim turnSign As Double = 0.0
            If smoothedTurnSignal > 0.0 Then
                turnSign = 1.0
            ElseIf smoothedTurnSignal < 0.0 Then
                turnSign = -1.0
            End If

            ' Roll authority follows speed. Hero holds settle naturally to <= about 2 deg,
            ' while a true fast whip can still bank strongly without looking like a flip.
            Dim speedNorm As Double = Math.Max(0.0, Math.Min(1.0, speedIntent / 280.0))
            Dim speedGate As Double = SmoothStep01(speedNorm)
            Dim maxBankCap As Double = Math.Max(0.0, Math.Min(25.0, maxBankUser))
            Dim holdBank As Double = Math.Min(2.0, maxBankCap)
            Dim maxRoll As Double = holdBank + Math.Max(0.0, maxBankCap - holdBank) * speedGate
            Dim rawRoll As Double = -turnSign * maxRoll * turnStrength * bankGain
            Dim bankDeg As Double = maxRoll * Math.Tanh(rawRoll / Math.Max(0.5, maxRoll))

            LastBankDeg = bankDeg
            Dim bankRad As Double = bankDeg * Math.PI / 180.0
            Return Vec3.RodriguesRotate(U_level, F_curr, bankRad).Normalize()
        End Function

        Public Function GetSmoothBankDeg() As Double
            Return LastBankDeg
        End Function
    End Class

    ' --------------------------------------------------------------------------
    ' 7. CANONICAL CAMERA SAMPLER (SINGLE SOURCE OF TRUTH)
    ' --------------------------------------------------------------------------
    Public Shared Function EvaluateTargetCatmullRom(ByVal s As Double, ByVal sKeys As Double(), ByVal tgtKeys As Vec3()) As Vec3
        s = Math.Max(0.0, Math.Min(1.0, s))
        Dim n As Integer = sKeys.Length

        For i As Integer = 0 To n - 2
            If s <= sKeys(i + 1) OrElse i = n - 2 Then
                Dim s0 As Double = sKeys(i)
                Dim s1 As Double = sKeys(i + 1)
                Dim ds As Double = s1 - s0
                Dim t As Double = If(ds > 1E-9, (s - s0) / ds, 0.0)
                t = Math.Max(0.0, Math.Min(1.0, t))

                Dim p0 As Vec3 = tgtKeys(Math.Max(0, i - 1))
                Dim p1 As Vec3 = tgtKeys(i)
                Dim p2 As Vec3 = tgtKeys(i + 1)
                Dim p3 As Vec3 = tgtKeys(Math.Min(n - 1, i + 2))

                Dim t2 As Double = t * t
                Dim t3 As Double = t2 * t

                Return 0.5 * ((2.0 * p1) + _
                              (p2 - p0) * t + _
                              (2.0 * p0 - 5.0 * p1 + 4.0 * p2 - p3) * t2 + _
                              (p3 - p0 + 3.0 * (p1 - p2)) * t3)
            End If
        Next

        Return tgtKeys(n - 1)
    End Function

    Public Function SampleCameraAtTime(ByVal t As Double, _
                                       ByVal rail As MasterSpatialRail, _
                                       ByVal speedLaw As JerkLimitedSpeedLaw, _
                                       ByVal orient As ParallelTransportOrientation, _
                                       ByVal model As ModelInfo, _
                                       ByVal heroes As List(Of HeroTarget), _
                                       ByVal settings As CameraSettings) As CameraState
        Dim state As New CameraState()

        ' 1. Evaluate S-curve normalized distance s in [0, 1]
        Dim s As Double = speedLaw.GetNormalizedDistance(t)
        state.Speed = speedLaw.EvaluateSpeed(t)
        state.Accel = speedLaw.EvaluateAcceleration(t)

        ' 2. Evaluate Spatial Rail Position, Tangent, and 2nd Derivative
        Dim railPos As New Vec3()
        Dim railTan As New Vec3()
        Dim railSecDeriv As New Vec3()
        rail.EvaluateRailAtDistance(s, railPos, railTan, railSecDeriv)
        state.Eye = railPos

        ' 3. RHYTHM-LOCKED HERO TARGETING.
        ' Target phase is derived from the same global-u Hero orbit as the Eye path,
        ' avoiding the old mismatch where Eye was in one Hero shot while target blending
        ' had already entered another shot.
        Dim H1 As HeroTarget = heroes(0)
        Dim H2 As HeroTarget = heroes(1)
        Dim H3 As HeroTarget = heroes(2)
        Dim H4 As HeroTarget = heroes(3)
        Dim skidCenter As Vec3 = model.Center + 0.08 * model.RH * model.W
        Dim uGlobal As Double = rail.InverseArcLength(s)

        Dim speedNorm As Double = Math.Max(0.0, Math.Min(1.0, state.Speed / 300.0))
        ' V5.10: tăng look-ahead base từ 0.010 -> 0.018 để ổn định target khi chậm
        Dim sLookAhead As Double = Math.Min(1.0, s + (0.018 + 0.070 * speedNorm) * (1.0 - 0.30 * s))
        Dim lookAheadPos As New Vec3()
        Dim dummy1 As New Vec3(), dummy2 As New Vec3()
        rail.EvaluateRailAtDistance(sLookAhead, lookAheadPos, dummy1, dummy2)

        Dim heroTargetPt As Vec3 = H1.Center
        Dim activeHero As HeroTarget = H1
        state.ActiveHeroName = "Pump System (Hero 1)"

        ' Smooth cross-fades happen only in short far/fast transition windows.
        If uGlobal < 16.0 Then
            heroTargetPt = H1.Center
            activeHero = H1
            state.ActiveHeroName = "Pump System (Hero 1)"
        ElseIf uGlobal < 19.0 Then
            ' V5.10: 3-phase neutral center - chống đảo ngang khi chuyển cảnh chậm
            Dim a As Double = (uGlobal - 16.0) / 3.0
            a = Math.Max(0.0, Math.Min(1.0, a))
            Dim nc12 As Vec3 = model.Center + 0.06 * model.RH * model.W
            Dim tA12 As Double = a / 0.35 : If tA12 > 1.0 Then tA12 = 1.0
            tA12 = tA12 * tA12 * (3.0 - 2.0 * tA12)
            Dim tB12 As Double = (a - 0.65) / 0.35 : If tB12 < 0.0 Then tB12 = 0.0 : If tB12 > 1.0 Then tB12 = 1.0
            tB12 = tB12 * tB12 * (3.0 - 2.0 * tB12)
            If a < 0.50 Then
                heroTargetPt = Vec3.Lerp(H1.Center, nc12, tA12)
            Else
                heroTargetPt = Vec3.Lerp(nc12, H2.Center, tB12)
            End If
            activeHero = If(a < 0.5, H1, H2)
            state.ActiveHeroName = If(a < 0.5, "Pump System (Hero 1)", "UF Membrane (Hero 2)")
        ElseIf uGlobal < 33.0 Then
            heroTargetPt = H2.Center
            activeHero = H2
            state.ActiveHeroName = "UF Membrane (Hero 2)"
        ElseIf uGlobal < 36.0 Then
            ' V5.10: 3-phase neutral center
            Dim a As Double = (uGlobal - 33.0) / 3.0
            a = Math.Max(0.0, Math.Min(1.0, a))
            Dim nc23 As Vec3 = model.Center + 0.06 * model.RH * model.W
            Dim tA23 As Double = a / 0.35 : If tA23 > 1.0 Then tA23 = 1.0
            tA23 = tA23 * tA23 * (3.0 - 2.0 * tA23)
            Dim tB23 As Double = (a - 0.65) / 0.35 : If tB23 < 0.0 Then tB23 = 0.0 : If tB23 > 1.0 Then tB23 = 1.0
            tB23 = tB23 * tB23 * (3.0 - 2.0 * tB23)
            If a < 0.50 Then
                heroTargetPt = Vec3.Lerp(H2.Center, nc23, tA23)
            Else
                heroTargetPt = Vec3.Lerp(nc23, H3.Center, tB23)
            End If
            activeHero = If(a < 0.5, H2, H3)
            state.ActiveHeroName = If(a < 0.5, "UF Membrane (Hero 2)", "Control Panel (Hero 3)")
        ElseIf uGlobal < 50.0 Then
            heroTargetPt = H3.Center
            activeHero = H3
            state.ActiveHeroName = "Control Panel (Hero 3)"
        ElseIf uGlobal < 53.0 Then
            ' V5.10: 3-phase neutral center
            Dim a As Double = (uGlobal - 50.0) / 3.0
            a = Math.Max(0.0, Math.Min(1.0, a))
            Dim nc34 As Vec3 = model.Center + 0.06 * model.RH * model.W
            Dim tA34 As Double = a / 0.35 : If tA34 > 1.0 Then tA34 = 1.0
            tA34 = tA34 * tA34 * (3.0 - 2.0 * tA34)
            Dim tB34 As Double = (a - 0.65) / 0.35 : If tB34 < 0.0 Then tB34 = 0.0 : If tB34 > 1.0 Then tB34 = 1.0
            tB34 = tB34 * tB34 * (3.0 - 2.0 * tB34)
            If a < 0.50 Then
                heroTargetPt = Vec3.Lerp(H3.Center, nc34, tA34)
            Else
                heroTargetPt = Vec3.Lerp(nc34, H4.Center, tB34)
            End If
            activeHero = If(a < 0.5, H3, H4)
            state.ActiveHeroName = If(a < 0.5, "Control Panel (Hero 3)", "UV & Manifold (Hero 4)")
        ElseIf uGlobal < 67.0 Then
            heroTargetPt = H4.Center
            activeHero = H4
            state.ActiveHeroName = "UV & Manifold (Hero 4)"
        Else
            Dim a As Double = (uGlobal - 67.0) / Math.Max(1.0, CDbl(rail.NumSegments) - 67.0)
            a = Math.Max(0.0, Math.Min(1.0, a))
            a = a * a * (3.0 - 2.0 * a)
            heroTargetPt = Vec3.Lerp(H4.Center, skidCenter, 0.55 * a)
            activeHero = H4
            state.ActiveHeroName = "Grand Overview"
        End If

        ' During near/slow inspection, almost lock the subject. During fast flight,
        ' allow more look-ahead so the motion reads as a circular sweep rather than a
        ' camera that mechanically stares at one point.
        Dim heroWeight As Double = 0.74 - 0.18 * speedNorm
        If speedNorm < 0.20 Then heroWeight = 0.97
        If uGlobal >= 67.0 Then heroWeight = Math.Min(heroWeight, 0.72)

        state.Target = Vec3.Lerp(lookAheadPos, heroTargetPt, heroWeight)

        ' 4. Cinematic banking with deterministic spatial curvature smoothing.
        ' Average turn direction over a small rail window so an inflection cannot make
        ' the camera instantly bank left -> right. This remains safe for out-of-order
        ' motion-blur sub-frame sampling because it has no frame-history dependency.
        Dim turnOffsets As Double() = {-0.040, -0.020, 0.0, 0.020, 0.040}  ' V5.10: wider window -> ổn định banking
        Dim turnWeights As Double() = {1.0, 2.0, 3.0, 2.0, 1.0}
        Dim turnWeighted As Double = 0.0
        Dim turnWeightSum As Double = 0.0
        For ti As Integer = 0 To turnOffsets.Length - 1
            Dim ss As Double = Math.Max(0.0, Math.Min(1.0, s + turnOffsets(ti)))
            Dim pTmp As New Vec3(), tTmp As New Vec3(), aTmp As New Vec3()
            rail.EvaluateRailAtDistance(ss, pTmp, tTmp, aTmp)
            Dim sig As Double = ParallelTransportOrientation.SignedTurnSignal(tTmp, aTmp, model.W)
            turnWeighted += sig * turnWeights(ti)
            turnWeightSum += turnWeights(ti)
        Next
        Dim smoothedTurn As Double = If(turnWeightSum > 0.0, turnWeighted / turnWeightSum, 0.0)

        Dim F_dir As Vec3 = (state.Target - state.Eye).Normalize()
        state.UpVector = orient.EvaluateOrientation(F_dir, model.W, smoothedTurn, state.Speed, settings.BankGainMultiplier, settings.MaxBankDegrees)
        state.RollDeg = orient.GetSmoothBankDeg()

        ' 5. PULSED perspective emphasis. Translation remains primary, but FOV now
        ' also reacts to REAL Hero proximity so the two near passes visually "hit".
        Dim heroLocalSize As Double = Math.Max(20.0, Math.Max(activeHero.SizeU, Math.Max(activeHero.SizeV, activeHero.SizeW)))
        Dim heroDist As Double = Vec3.Distance(state.Eye, activeHero.Center)
        Dim nearStart As Double = 0.55 * heroLocalSize
        Dim nearEnd As Double = 1.85 * heroLocalSize
        Dim nearNorm As Double = 1.0 - Math.Max(0.0, Math.Min(1.0, (heroDist - nearStart) / Math.Max(1E-6, nearEnd - nearStart)))
        Dim fovFar As Double = Math.Max(20.0, Math.Min(100.0, settings.FOVFarDegrees))
        Dim fovFast As Double = Math.Max(20.0, Math.Min(110.0, settings.FOVFastDegrees))
        Dim fovNear As Double = Math.Max(20.0, Math.Min(110.0, settings.FOVNearDegrees))
        Dim fovReveal As Double = Math.Max(20.0, Math.Min(100.0, settings.FOVRevealDegrees))
        Dim fovBySpeed As Double = fovFar + (fovFast - fovFar) * Math.Pow(speedNorm, 0.72)
        Dim fovByNear As Double = fovFar + (fovNear - fovFar) * Math.Pow(nearNorm, 1.20)
        Dim fovBase As Double = Math.Max(fovBySpeed, fovByNear)
        If s >= 0.86 Then
            Dim ts As Double = Math.Max(0.0, Math.Min(1.0, (s - 0.86) / 0.14))
            Dim smoothReveal As Double = ts * ts * (3.0 - 2.0 * ts)
            fovBase = fovBase * (1.0 - smoothReveal) + fovReveal * smoothReveal
        End If
        Dim fovMin As Double = Math.Min(fovReveal, Math.Min(fovFar, Math.Min(fovFast, fovNear)))
        Dim fovMax As Double = Math.Max(fovReveal, Math.Max(fovFar, Math.Max(fovFast, fovNear)))
        state.FOV = Math.Max(fovMin, Math.Min(fovMax, fovBase))

        Return state
    End Function

    ' --------------------------------------------------------------------------
    ' 8. CORE COMPONENT & OCCURRENCE SCANNER (TRUE INVENTOR Y-UP GEOMETRY)
    ' --------------------------------------------------------------------------
    Private Sub AccumulateVisibleOccurrenceBounds(ByVal occ As ComponentOccurrence, _
                                                     ByRef haveBounds As Boolean, _
                                                     ByRef minX As Double, ByRef minY As Double, ByRef minZ As Double, _
                                                     ByRef maxX As Double, ByRef maxY As Double, ByRef maxZ As Double)
        Try
            If occ.Suppressed Then Return
            If Not occ.Visible Then Return
        Catch
            Return
        End Try

        Dim hasChildren As Boolean = False
        Try
            hasChildren = (occ.SubOccurrences.Count > 0)
        Catch
            hasChildren = False
        End Try

        If hasChildren Then
            Try
                For Each child As ComponentOccurrence In occ.SubOccurrences
                    AccumulateVisibleOccurrenceBounds(child, haveBounds, minX, minY, minZ, maxX, maxY, maxZ)
                Next
            Catch
            End Try
            Return
        End If

        Try
            Dim box As Box = occ.RangeBox
            If Not haveBounds Then
                minX = box.MinPoint.X : minY = box.MinPoint.Y : minZ = box.MinPoint.Z
                maxX = box.MaxPoint.X : maxY = box.MaxPoint.Y : maxZ = box.MaxPoint.Z
                haveBounds = True
            Else
                minX = Math.Min(minX, box.MinPoint.X)
                minY = Math.Min(minY, box.MinPoint.Y)
                minZ = Math.Min(minZ, box.MinPoint.Z)
                maxX = Math.Max(maxX, box.MaxPoint.X)
                maxY = Math.Max(maxY, box.MaxPoint.Y)
                maxZ = Math.Max(maxZ, box.MaxPoint.Z)
            End If
        Catch
        End Try
    End Sub

    Public Function AnalyzeModel(ByVal oDoc As Document) As ModelInfo
        Dim info As New ModelInfo()
        ' TRUE AUTODESK INVENTOR COORDINATES: Y IS VERTICAL HEIGHT UP!
        info.U = New Vec3(1, 0, 0) ' X-axis: Width (Left <-> Right)
        info.V = New Vec3(0, 0, 1) ' Z-axis: Length / Depth (Front <-> Back)
        info.W = New Vec3(0, 1, 0) ' Y-axis: Vertical Height (Ground -> Sky UP)

        Dim minPt As Inventor.Point = Nothing
        Dim maxPt As Inventor.Point = Nothing

        ' V5.7: assembly bounds are derived from CURRENTLY VISIBLE leaf occurrences.
        ' Hidden components must not move the camera center or enlarge the flight envelope.
        If oDoc.DocumentType = DocumentTypeEnum.kAssemblyDocumentObject Then
            Try
                Dim oAsm As AssemblyDocument = CType(oDoc, AssemblyDocument)
                Dim haveBounds As Boolean = False
                Dim minX As Double = 0.0, minY As Double = 0.0, minZ As Double = 0.0
                Dim maxX As Double = 0.0, maxY As Double = 0.0, maxZ As Double = 0.0

                For Each occ As ComponentOccurrence In oAsm.ComponentDefinition.Occurrences
                    AccumulateVisibleOccurrenceBounds(occ, haveBounds, minX, minY, minZ, maxX, maxY, maxZ)
                Next

                If haveBounds Then
                    minPt = ThisApplication.TransientGeometry.CreatePoint(minX, minY, minZ)
                    maxPt = ThisApplication.TransientGeometry.CreatePoint(maxX, maxY, maxZ)
                Else
                    minPt = oAsm.ComponentDefinition.RangeBox.MinPoint
                    maxPt = oAsm.ComponentDefinition.RangeBox.MaxPoint
                End If
            Catch
            End Try
        ElseIf oDoc.DocumentType = DocumentTypeEnum.kPartDocumentObject Then
            Try
                Dim oPrt As PartDocument = CType(oDoc, PartDocument)
                minPt = oPrt.ComponentDefinition.RangeBox.MinPoint
                maxPt = oPrt.ComponentDefinition.RangeBox.MaxPoint
            Catch
            End Try
        End If

        If minPt Is Nothing OrElse maxPt Is Nothing Then
            Dim oCam As Camera = ThisApplication.ActiveView.Camera
            Dim centerPt As Inventor.Point = oCam.Target
            minPt = ThisApplication.TransientGeometry.CreatePoint(centerPt.X - 80, centerPt.Y - 80, centerPt.Z - 80)
            maxPt = ThisApplication.TransientGeometry.CreatePoint(centerPt.X + 80, centerPt.Y + 80, centerPt.Z + 80)
        End If

        info.Center = New Vec3((minPt.X + maxPt.X) * 0.5, (minPt.Y + maxPt.Y) * 0.5, (minPt.Z + maxPt.Z) * 0.5)
        info.RU = Math.Max(25.0, (maxPt.X - minPt.X) * 0.5)
        info.RV = Math.Max(25.0, (maxPt.Z - minPt.Z) * 0.5)
        info.RH = Math.Max(30.0, (maxPt.Y - minPt.Y) * 0.5)

        Return info
    End Function

    Private Sub CollectVisibleOccurrencesRecursive(ByVal occ As ComponentOccurrence, ByVal result As List(Of ComponentOccurrence))
        Try
            If occ.Suppressed Then Return
            If Not occ.Visible Then Return
        Catch
            Return
        End Try

        Dim hasChildren As Boolean = False
        Try
            hasChildren = (occ.SubOccurrences.Count > 0)
        Catch
            hasChildren = False
        End Try

        If hasChildren Then
            Try
                For Each child As ComponentOccurrence In occ.SubOccurrences
                    CollectVisibleOccurrencesRecursive(child, result)
                Next
            Catch
            End Try
        Else
            result.Add(occ)
        End If
    End Sub

    Public Function FindHeroAndForegroundTargets(ByVal oDoc As Document, ByVal model As ModelInfo) As List(Of HeroTarget)
        Dim targets As New List(Of HeroTarget)()
        If oDoc.DocumentType <> DocumentTypeEnum.kAssemblyDocumentObject Then
            For i As Integer = 1 To 4
                Dim dummy As New HeroTarget()
                dummy.Name = "Hero " & i.ToString()
                dummy.Center = model.Center
                dummy.AdaptiveClearance = 25.0
                targets.Add(dummy)
            Next
            Return targets
        End If

        Dim oAsm As AssemblyDocument = CType(oDoc, AssemblyDocument)
        Dim pumpOcc As ComponentOccurrence = Nothing
        Dim ufOcc As ComponentOccurrence = Nothing
        Dim panelOcc As ComponentOccurrence = Nothing
        Dim uvOcc As ComponentOccurrence = Nothing

        Dim visibleOccurrences As New List(Of ComponentOccurrence)()
        For Each rootOcc As ComponentOccurrence In oAsm.ComponentDefinition.Occurrences
            CollectVisibleOccurrencesRecursive(rootOcc, visibleOccurrences)
        Next

        ' V5.7: hidden/suppressed components can never become Hero targets.
        For Each occ As ComponentOccurrence In visibleOccurrences
            Try
                Dim n As String = occ.Name.ToLower()
                If pumpOcc Is Nothing AndAlso (n.Contains("bom") OrElse n.Contains("pump")) Then pumpOcc = occ
                If ufOcc Is Nothing AndAlso (n.Contains("uf") OrElse n.Contains("membrane")) Then ufOcc = occ
                If panelOcc Is Nothing AndAlso (n.Contains("hop") OrElse n.Contains("panel") OrElse n.Contains("dien")) Then panelOcc = occ
                If uvOcc Is Nothing AndAlso (n.Contains("uv") OrElse n.Contains("den")) Then uvOcc = occ
            Catch
            End Try
        Next

        Dim occs As ComponentOccurrence() = {pumpOcc, ufOcc, panelOcc, uvOcc}
        Dim names As String() = {"Pump System", "UF Membrane", "Control Panel", "UV Disinfection"}
        Dim offsets As Double(,) = {{ -0.35, -0.65, 0.12 }, { 0.10, -0.70, 0.35 }, { 0.65, 0.10, 0.50 }, { -0.15, 0.70, 0.28 }}

        For i As Integer = 0 To 3
            Dim ht As New HeroTarget()
            ht.Name = names(i)
            ht.Occurrence = occs(i)
            If occs(i) IsNot Nothing Then
                Try
                    Dim box As Box = occs(i).RangeBox
                    ht.MinPt = New Vec3(box.MinPoint.X, box.MinPoint.Y, box.MinPoint.Z)
                    ht.MaxPt = New Vec3(box.MaxPoint.X, box.MaxPoint.Y, box.MaxPoint.Z)
                    ht.Center = New Vec3((box.MinPoint.X + box.MaxPoint.X) * 0.5, (box.MinPoint.Y + box.MaxPoint.Y) * 0.5, (box.MinPoint.Z + box.MaxPoint.Z) * 0.5)
                    ht.SizeU = Math.Abs(box.MaxPoint.X - box.MinPoint.X)
                    ht.SizeV = Math.Abs(box.MaxPoint.Z - box.MinPoint.Z)
                    ht.SizeW = Math.Abs(box.MaxPoint.Y - box.MinPoint.Y)
                    Dim diag As Double = Math.Sqrt(ht.SizeU * ht.SizeU + ht.SizeV * ht.SizeV + ht.SizeW * ht.SizeW)
                    ht.AdaptiveClearance = Math.Max(10.0, Math.Min(30.0, diag * 0.14))
                Catch
                    ht.Center = model.Center + offsets(i, 0) * model.RU * model.U + offsets(i, 1) * model.RV * model.V + offsets(i, 2) * model.RH * model.W
                    ht.AdaptiveClearance = 25.0
                End Try
            Else
                ht.Center = model.Center + offsets(i, 0) * model.RU * model.U + offsets(i, 1) * model.RV * model.V + offsets(i, 2) * model.RH * model.W
                ht.AdaptiveClearance = 25.0
            End If
            If ht.SizeU <= 0.0 Then ht.SizeU = Math.Max(20.0, model.RU * 0.35)
            If ht.SizeV <= 0.0 Then ht.SizeV = Math.Max(20.0, model.RV * 0.25)
            If ht.SizeW <= 0.0 Then ht.SizeW = Math.Max(20.0, model.RH * 0.45)
            targets.Add(ht)
        Next

        Return targets
    End Function

    ' --------------------------------------------------------------------------
    ' 9. DESIGN-VIEW SAFE RENDER GUARD (V5.9)
    '    IMPORTANT:
    '    - Never rewrite ComponentOccurrence.Visible during rendering.
    '      Visibility may be controlled by the active Design View Representation,
    '      including associative visibility inside subassemblies.
    '    - Hide construction/UI geometry through Document.ObjectVisibility instead.
    '    - Preserve the active Design View and re-assert only if Inventor changes it.
    ' --------------------------------------------------------------------------
    Public Class ObjectVisibilityState
        Public Vis As ObjectVisibility
        Public AllWorkFeatures As Boolean
        Public Annotations3D As Boolean
        Public ComponentAnnotations3D As Boolean
        Public ConstructionSurfaces As Boolean
        Public GroupDiagnostics As Boolean
        Public GroupSurfaces As Boolean
        Public GroupWires As Boolean
        Public OriginWorkAxes As Boolean
        Public OriginWorkPlanes As Boolean
        Public OriginWorkPoints As Boolean
        Public SketchDimensions As Boolean
        Public Sketches As Boolean
        Public Sketches3D As Boolean
        Public UCSTriads As Boolean
        Public UCSWorkAxes As Boolean
        Public UCSWorkPlanes As Boolean
        Public UCSWorkPoints As Boolean
        Public UserWorkAxes As Boolean
        Public UserWorkPlanes As Boolean
        Public UserWorkPoints As Boolean
        Public WeldmentSymbols As Boolean
    End Class

    Public Class RenderStateSnapshot
        Public ActiveDesignView As DesignViewRepresentation = Nothing
        Public ActiveDesignViewName As String = ""
        Public VisibilityStates As New List(Of ObjectVisibilityState)()
    End Class

    Private Function GetDocumentObjectVisibility(ByVal doc As Document) As ObjectVisibility
        Try
            If doc.DocumentType = DocumentTypeEnum.kAssemblyDocumentObject Then
                Return CType(doc, AssemblyDocument).ObjectVisibility
            ElseIf doc.DocumentType = DocumentTypeEnum.kPartDocumentObject Then
                Return CType(doc, PartDocument).ObjectVisibility
            End If
        Catch
        End Try
        Return Nothing
    End Function

    Private Function CaptureObjectVisibility(ByVal doc As Document) As ObjectVisibilityState
        Dim vis As ObjectVisibility = GetDocumentObjectVisibility(doc)
        If vis Is Nothing Then Return Nothing

        Dim st As New ObjectVisibilityState()
        st.Vis = vis
        Try : st.AllWorkFeatures = vis.AllWorkFeatures : Catch : End Try
        Try : st.Annotations3D = vis.Annotations3D : Catch : End Try
        Try : st.ComponentAnnotations3D = vis.ComponentAnnotations3D : Catch : End Try
        Try : st.ConstructionSurfaces = vis.ConstructionSurfaces : Catch : End Try
        Try : st.GroupDiagnostics = vis.GroupDiagnostics : Catch : End Try
        Try : st.GroupSurfaces = vis.GroupSurfaces : Catch : End Try
        Try : st.GroupWires = vis.GroupWires : Catch : End Try
        Try : st.OriginWorkAxes = vis.OriginWorkAxes : Catch : End Try
        Try : st.OriginWorkPlanes = vis.OriginWorkPlanes : Catch : End Try
        Try : st.OriginWorkPoints = vis.OriginWorkPoints : Catch : End Try
        Try : st.SketchDimensions = vis.SketchDimensions : Catch : End Try
        Try : st.Sketches = vis.Sketches : Catch : End Try
        Try : st.Sketches3D = vis.Sketches3D : Catch : End Try
        Try : st.UCSTriads = vis.UCSTriads : Catch : End Try
        Try : st.UCSWorkAxes = vis.UCSWorkAxes : Catch : End Try
        Try : st.UCSWorkPlanes = vis.UCSWorkPlanes : Catch : End Try
        Try : st.UCSWorkPoints = vis.UCSWorkPoints : Catch : End Try
        Try : st.UserWorkAxes = vis.UserWorkAxes : Catch : End Try
        Try : st.UserWorkPlanes = vis.UserWorkPlanes : Catch : End Try
        Try : st.UserWorkPoints = vis.UserWorkPoints : Catch : End Try
        Try : st.WeldmentSymbols = vis.WeldmentSymbols : Catch : End Try
        Return st
    End Function

    Private Sub ForceCleanObjectVisibility(ByVal st As ObjectVisibilityState)
        If st Is Nothing OrElse st.Vis Is Nothing Then Return
        Dim vis As ObjectVisibility = st.Vis

        ' Global switches first, then explicit categories. This catches origin planes,
        ' user planes, UCS geometry, referenced sketches and construction surfaces.
        Try : vis.AllWorkFeatures = False : Catch : End Try
        Try : vis.Annotations3D = False : Catch : End Try
        Try : vis.ComponentAnnotations3D = False : Catch : End Try
        Try : vis.ConstructionSurfaces = False : Catch : End Try
        Try : vis.GroupDiagnostics = False : Catch : End Try
        Try : vis.GroupSurfaces = False : Catch : End Try
        Try : vis.GroupWires = False : Catch : End Try
        Try : vis.OriginWorkAxes = False : Catch : End Try
        Try : vis.OriginWorkPlanes = False : Catch : End Try
        Try : vis.OriginWorkPoints = False : Catch : End Try
        Try : vis.SketchDimensions = False : Catch : End Try
        Try : vis.Sketches = False : Catch : End Try
        Try : vis.Sketches3D = False : Catch : End Try
        Try : vis.UCSTriads = False : Catch : End Try
        Try : vis.UCSWorkAxes = False : Catch : End Try
        Try : vis.UCSWorkPlanes = False : Catch : End Try
        Try : vis.UCSWorkPoints = False : Catch : End Try
        Try : vis.UserWorkAxes = False : Catch : End Try
        Try : vis.UserWorkPlanes = False : Catch : End Try
        Try : vis.UserWorkPoints = False : Catch : End Try
        Try : vis.WeldmentSymbols = False : Catch : End Try
    End Sub

    Private Sub RestoreObjectVisibility(ByVal st As ObjectVisibilityState)
        If st Is Nothing OrElse st.Vis Is Nothing Then Return
        Dim vis As ObjectVisibility = st.Vis
        Try : vis.AllWorkFeatures = st.AllWorkFeatures : Catch : End Try
        Try : vis.Annotations3D = st.Annotations3D : Catch : End Try
        Try : vis.ComponentAnnotations3D = st.ComponentAnnotations3D : Catch : End Try
        Try : vis.ConstructionSurfaces = st.ConstructionSurfaces : Catch : End Try
        Try : vis.GroupDiagnostics = st.GroupDiagnostics : Catch : End Try
        Try : vis.GroupSurfaces = st.GroupSurfaces : Catch : End Try
        Try : vis.GroupWires = st.GroupWires : Catch : End Try
        Try : vis.OriginWorkAxes = st.OriginWorkAxes : Catch : End Try
        Try : vis.OriginWorkPlanes = st.OriginWorkPlanes : Catch : End Try
        Try : vis.OriginWorkPoints = st.OriginWorkPoints : Catch : End Try
        Try : vis.SketchDimensions = st.SketchDimensions : Catch : End Try
        Try : vis.Sketches = st.Sketches : Catch : End Try
        Try : vis.Sketches3D = st.Sketches3D : Catch : End Try
        Try : vis.UCSTriads = st.UCSTriads : Catch : End Try
        Try : vis.UCSWorkAxes = st.UCSWorkAxes : Catch : End Try
        Try : vis.UCSWorkPlanes = st.UCSWorkPlanes : Catch : End Try
        Try : vis.UCSWorkPoints = st.UCSWorkPoints : Catch : End Try
        Try : vis.UserWorkAxes = st.UserWorkAxes : Catch : End Try
        Try : vis.UserWorkPlanes = st.UserWorkPlanes : Catch : End Try
        Try : vis.UserWorkPoints = st.UserWorkPoints : Catch : End Try
        Try : vis.WeldmentSymbols = st.WeldmentSymbols : Catch : End Try
    End Sub

    Public Function PrepareRenderState(ByVal oDoc As Document, ByVal settings As CameraSettings) As RenderStateSnapshot
        Dim snap As New RenderStateSnapshot()

        ' Preserve the exact active Design View. DO NOT touch occurrence.Visible.
        If oDoc.DocumentType = DocumentTypeEnum.kAssemblyDocumentObject Then
            Try
                Dim oAsm As AssemblyDocument = CType(oDoc, AssemblyDocument)
                snap.ActiveDesignView = oAsm.ComponentDefinition.RepresentationsManager.ActiveDesignViewRepresentation
                If snap.ActiveDesignView IsNot Nothing Then snap.ActiveDesignViewName = snap.ActiveDesignView.Name
            Catch
            End Try
        End If

        ' Clear selection/highlight. A selected hidden work feature can remain graphically
        ' emphasized even when ordinary visibility is off.
        Try : oDoc.SelectSet.Clear() : Catch : End Try

        If settings.HideConstructionGeometryDuringRender Then
            Dim rootState As ObjectVisibilityState = CaptureObjectVisibility(oDoc)
            If rootState IsNot Nothing Then
                snap.VisibilityStates.Add(rootState)
                ForceCleanObjectVisibility(rootState)
            End If

            ' Referenced documents can carry their own work-feature display flags.
            ' Snapshot/disable them too, then restore in Finally.
            Try
                For Each refDoc As Document In oDoc.AllReferencedDocuments
                    Dim refState As ObjectVisibilityState = CaptureObjectVisibility(refDoc)
                    If refState IsNot Nothing Then
                        snap.VisibilityStates.Add(refState)
                        ForceCleanObjectVisibility(refState)
                    End If
                Next
            Catch
            End Try
        End If

        Return snap
    End Function

    Private Sub EnsureOriginalDesignView(ByVal oDoc As Document, ByVal snap As RenderStateSnapshot)
        If snap Is Nothing OrElse snap.ActiveDesignView Is Nothing Then Return
        If oDoc.DocumentType <> DocumentTypeEnum.kAssemblyDocumentObject Then Return

        Try
            Dim oAsm As AssemblyDocument = CType(oDoc, AssemblyDocument)
            Dim currentRep As DesignViewRepresentation = oAsm.ComponentDefinition.RepresentationsManager.ActiveDesignViewRepresentation
            If currentRep Is Nothing OrElse currentRep.Name <> snap.ActiveDesignViewName Then
                snap.ActiveDesignView.Activate()
            End If
        Catch
        End Try
    End Sub

    Public Sub EnforceRenderState(ByVal oDoc As Document, ByVal snap As RenderStateSnapshot, ByVal settings As CameraSettings)
        If snap Is Nothing Then Return

        ' Re-assert the user's Design View only if Inventor unexpectedly switched it.
        ' We never set individual occurrence visibility here.
        If settings.PreserveCurrentOccurrenceVisibility Then
            EnsureOriginalDesignView(oDoc, snap)
        End If

        If settings.HideConstructionGeometryDuringRender Then
            For Each st As ObjectVisibilityState In snap.VisibilityStates
                ForceCleanObjectVisibility(st)
            Next
        End If

        Try : oDoc.SelectSet.Clear() : Catch : End Try
    End Sub

    Public Sub RestoreRenderState(ByVal oDoc As Document, ByVal snap As RenderStateSnapshot)
        If snap Is Nothing Then Return

        ' Restore global object visibility first.
        For Each st As ObjectVisibilityState In snap.VisibilityStates
            RestoreObjectVisibility(st)
        Next

        ' Return to the user's original Design View if necessary.
        EnsureOriginalDesignView(oDoc, snap)
    End Sub

    Public Sub ApplyCameraAndCaptureFrame(ByVal oDoc As Document, _
                                          ByVal oApp As Inventor.Application, _
                                          ByVal oCam As Camera, _
                                          ByVal tg As TransientGeometry, _
                                          ByVal state As CameraState, _
                                          ByVal framePath As String, _
                                          ByVal settings As CameraSettings, _
                                          ByVal renderSnapshot As RenderStateSnapshot)
        ' 1) Lock design view + clean object visibility BEFORE camera update.
        EnforceRenderState(oDoc, renderSnapshot, settings)

        ' 2) Apply cinematic camera. This must be the only per-frame model-view mutation.
        oCam.Eye = tg.CreatePoint(state.Eye.X, state.Eye.Y, state.Eye.Z)
        oCam.Target = tg.CreatePoint(state.Target.X, state.Target.Y, state.Target.Z)
        oCam.UpVector = tg.CreateUnitVector(state.UpVector.X, state.UpVector.Y, state.UpVector.Z)
        oCam.Perspective = True
        oCam.PerspectiveAngle = state.FOV * Math.PI / 180.0
        oCam.ApplyWithoutTransition()

        ' 3) Re-assert display-only flags after camera apply, then force two graphics passes.
        '    The second pass avoids a stale overlay/selection buffer appearing in the bitmap.
        EnforceRenderState(oDoc, renderSnapshot, settings)
        Try : oApp.ActiveView.Update() : Catch : End Try
        System.Windows.Forms.Application.DoEvents()
        Try : oApp.ActiveView.Update() : Catch : End Try

        ' 4) Capture exactly the active viewport. Never use Camera.SaveAsBitmap in V5.9.
        oApp.ActiveView.SaveAsBitmap(framePath, settings.Width, settings.Height)
    End Sub

    ' --------------------------------------------------------------------------
    ' 10. WEIGHTED MOTION BLUR BLENDER
    ' --------------------------------------------------------------------------
    Public Function BlendBitmapsWeighted(ByVal bitmaps As List(Of System.Drawing.Bitmap)) As System.Drawing.Bitmap
        Dim n As Integer = bitmaps.Count
        If n = 1 Then Return New System.Drawing.Bitmap(bitmaps(0))

        Dim w As Integer = bitmaps(0).Width
        Dim h As Integer = bitmaps(0).Height
        Dim result As New System.Drawing.Bitmap(w, h, PixelFormat.Format32bppArgb)

        Dim weights(n - 1) As Double
        Dim sumW As Double = 0.0
        For i As Integer = 0 To n - 1
            Dim normIdx As Double = CDbl(i) / CDbl(Math.Max(1, n - 1))
            Dim wt As Double = 1.0 - Math.Abs(normIdx - 0.5) * 1.5
            If wt < 0.2 Then wt = 0.2
            weights(i) = wt
            sumW += wt
        Next
        For i As Integer = 0 To n - 1 : weights(i) /= sumW : Next

        Dim rect As New System.Drawing.Rectangle(0, 0, w, h)
        Dim resData As BitmapData = result.LockBits(rect, ImageLockMode.WriteOnly, PixelFormat.Format32bppArgb)
        Dim numPixels As Integer = w * h
        Dim totalBytes As Integer = numPixels * 4
        Dim pixelBuffers As New List(Of Byte())()

        For Each bmp As System.Drawing.Bitmap In bitmaps
            Dim bData As BitmapData = bmp.LockBits(rect, ImageLockMode.ReadOnly, PixelFormat.Format32bppArgb)
            Dim buf(totalBytes - 1) As Byte
            Marshal.Copy(bData.Scan0, buf, 0, totalBytes)
            bmp.UnlockBits(bData)
            pixelBuffers.Add(buf)
        Next

        Dim finalBuf(totalBytes - 1) As Byte
        For p As Integer = 0 To numPixels - 1
            Dim bIdx As Integer = p * 4
            Dim bSum As Double = 0.0, gSum As Double = 0.0, rSum As Double = 0.0
            For s As Integer = 0 To n - 1
                Dim buf As Byte() = pixelBuffers(s)
                Dim sw As Double = weights(s)
                bSum += CDbl(buf(bIdx)) * sw
                gSum += CDbl(buf(bIdx + 1)) * sw
                rSum += CDbl(buf(bIdx + 2)) * sw
            Next
            finalBuf(bIdx) = CByte(Math.Min(255.0, bSum))
            finalBuf(bIdx + 1) = CByte(Math.Min(255.0, gSum))
            finalBuf(bIdx + 2) = CByte(Math.Min(255.0, rSum))
            finalBuf(bIdx + 3) = 255
        Next

        Marshal.Copy(finalBuf, 0, resData.Scan0, totalBytes)
        result.UnlockBits(resData)
        Return result
    End Function

    ' --------------------------------------------------------------------------
    ' 11. FFMPEG ENCODER
    ' --------------------------------------------------------------------------
    Public Sub EncodeVideoWithFFmpeg(ByVal outputDir As String, ByVal settings As CameraSettings, ByVal logPath As String)
        Dim ffmpegExe As String = "C:\\ProgramData\\chocolatey\\bin\\ffmpeg.exe"
        If Not System.IO.File.Exists(ffmpegExe) Then ffmpegExe = "ffmpeg.exe"

        Dim inputPattern As String = System.IO.Path.Combine(outputDir, "WT3D_Frame_%04d.png")
        Dim mp4Output As String = System.IO.Path.Combine(outputDir, "WT3D_Cinematic_V5_9_VietnameseControls.mp4")

        Dim audioArgs As String = ""
        Dim audioCandidates As String() = { _
            "D:\\WT3D_Project\\industrial-3d-models\\04_AUDIO_STUDIO\\02_Processed_Shorts_Audio\\CAM3_Phonk.mp3", _
            "D:\\WT3D_Project\\Z_Tools\\CAM3_Phonk.mp3" _
        }
        For Each ac As String In audioCandidates
            If System.IO.File.Exists(ac) Then
                audioArgs = " -i """ & ac & """ -c:a aac -b:a 192k -shortest"
                Exit For
            End If
        Next

        Dim ffmpegArgs As String = "-y -framerate " & settings.FPS.ToString() & _
                                   " -i """ & inputPattern & """" & audioArgs & _
                                   " -c:v libx264 -preset slow -crf 17 -pix_fmt yuv420p" & _
                                   " -movflags +faststart """ & mp4Output & """"

        Try
            Dim psi As New ProcessStartInfo(ffmpegExe, ffmpegArgs)
            psi.CreateNoWindow = True
            psi.UseShellExecute = False
            Dim p As Process = Process.Start(psi)
            p.WaitForExit()

            If System.IO.File.Exists(mp4Output) Then
                Try
                    Dim frameFiles As String() = System.IO.Directory.GetFiles(outputDir, "WT3D_Frame_*.png")
                    For Each ff As String In frameFiles : System.IO.File.Delete(ff) : Next
                Catch
                End Try
                Process.Start("explorer.exe", "/select,""" & mp4Output & """")
            End If
        Catch ex As Exception
            System.IO.File.AppendAllText(logPath, "FFmpeg error: " & ex.Message & vbCrLf)
        End Try
    End Sub

    ' --------------------------------------------------------------------------
    ' 12. EXECUTE DIRECTOR (PREVIEW & EXPORT)
    ' --------------------------------------------------------------------------
    Public Sub ExecuteDirector(ByVal oDoc As Document, ByVal oCam As Camera, ByVal settings As CameraSettings)
        Dim oApp As Inventor.Application = ThisApplication
        Dim tg As TransientGeometry = oApp.TransientGeometry

        ' ----------------------------------------------------------------------
        ' V5.9 DESIGN-VIEW SAFE VIDEO PIPELINE
        ' 1) Activate source document.
        ' 2) Preserve the active Design View Representation without editing occurrence visibility.
        ' 3) Hide work features/sketches/UCS/annotations through Document.ObjectVisibility.
        ' 4) Build camera only from visible geometry.
        ' 5) Before EVERY frame, re-assert Design View + display flags and update ActiveView twice.
        ' 6) Capture ActiveView, not a detached render state.
        ' 7) Restore ObjectVisibility + original Design View even on ESC/error.
        ' ----------------------------------------------------------------------
        Try : oDoc.Activate() : Catch : End Try

        Dim renderSnapshot As RenderStateSnapshot = Nothing
        Dim aborted As Boolean = False
        Dim frameCountDone As Integer = 0
        Dim outputDir As String = System.IO.Path.Combine(System.IO.Path.GetDirectoryName(oDoc.FullFileName), "WT3D_Camera_Output")
        System.IO.Directory.CreateDirectory(outputDir)
        Dim logPath As String = System.IO.Path.Combine(outputDir, "WT3D_Director.log")
        Dim telemetryCsv As String = System.IO.Path.Combine(outputDir, "WT3D_Telemetry_V5_9.csv")

        Try
            renderSnapshot = PrepareRenderState(oDoc, settings)
            Try : oApp.ActiveView.Update() : Catch : End Try
            System.Windows.Forms.Application.DoEvents()

            Dim model As ModelInfo = AnalyzeModel(oDoc)
            Dim heroes As List(Of HeroTarget) = FindHeroAndForegroundTargets(oDoc, model)

            Dim rail As New MasterSpatialRail()
            rail.BuildRail(model, heroes, settings)

            Dim speedLaw As New JerkLimitedSpeedLaw()
            speedLaw.Initialize(settings.DurationSeconds, rail, settings)

            Dim orient As New ParallelTransportOrientation()
            orient.Reset()

            System.IO.File.WriteAllText(telemetryCsv, "Frame,Time,Hero,EyeX,EyeY,EyeZ,TgtX,TgtY,TgtZ,Speed,Accel,RollDeg,FOV" & vbCrLf)

            If settings.RunMode = "PREVIEW" Then
                Dim swPreview As Stopwatch = Stopwatch.StartNew()
                Dim lastRenderTime As Double = -1.0
                Dim targetFrameInterval As Double = 1.0 / CDbl(settings.FPS)

                While swPreview.Elapsed.TotalSeconds < settings.DurationSeconds
                    If CheckEscapeKey() Then
                        aborted = True
                        Exit While
                    End If

                    Dim curT As Double = swPreview.Elapsed.TotalSeconds
                    If curT - lastRenderTime >= targetFrameInterval Then
                        lastRenderTime = curT
                        Dim state As CameraState = SampleCameraAtTime(curT, rail, speedLaw, orient, model, heroes, settings)

                        oCam.Eye = tg.CreatePoint(state.Eye.X, state.Eye.Y, state.Eye.Z)
                        oCam.Target = tg.CreatePoint(state.Target.X, state.Target.Y, state.Target.Z)
                        oCam.UpVector = tg.CreateUnitVector(state.UpVector.X, state.UpVector.Y, state.UpVector.Z)
                        oCam.Perspective = True
                        oCam.PerspectiveAngle = state.FOV * Math.PI / 180.0
                        oCam.ApplyWithoutTransition()

                        EnforceRenderState(oDoc, renderSnapshot, settings)
                        Try : oApp.ActiveView.Update() : Catch : End Try
                        System.Windows.Forms.Application.DoEvents()
                    Else
                        System.Threading.Thread.Sleep(1)
                    End If
                End While
                swPreview.Stop()

            Else
                ' Remove stale frames from previous runs. Without this, FFmpeg can append
                ' old frames when the new render has a shorter duration/frame count.
                Try
                    For Each oldFrame As String In System.IO.Directory.GetFiles(outputDir, "WT3D_Frame_*.png")
                        System.IO.File.Delete(oldFrame)
                    Next
                    For Each oldSub As String In System.IO.Directory.GetFiles(outputDir, "sub_*.png")
                        System.IO.File.Delete(oldSub)
                    Next
                Catch
                End Try

                For frame As Integer = 1 To settings.TotalFrames
                    If CheckEscapeKey() Then
                        aborted = True
                        Exit For
                    End If

                    Dim currentT As Double = CDbl(frame - 1) / CDbl(Math.Max(1, settings.TotalFrames - 1)) * settings.DurationSeconds
                    Dim state As CameraState = SampleCameraAtTime(currentT, rail, speedLaw, orient, model, heroes, settings)

                    Try
                        Dim line As String = String.Format("{0},{1:F3},{2},{3:F1},{4:F1},{5:F1},{6:F1},{7:F1},{8:F1},{9:F1},{10:F1},{11:F1},{12:F1}" & vbCrLf, _
                                             frame, currentT, state.ActiveHeroName, state.Eye.X, state.Eye.Y, state.Eye.Z, _
                                             state.Target.X, state.Target.Y, state.Target.Z, state.Speed, state.Accel, state.RollDeg, state.FOV)
                        System.IO.File.AppendAllText(telemetryCsv, line)
                    Catch
                    End Try

                    Dim frameName As String = "WT3D_Frame_" & frame.ToString("D4") & ".png"
                    Dim framePath As String = System.IO.Path.Combine(outputDir, frameName)

                    Dim blurSamples As Integer = If(settings.EnableMotionBlur, 3, 1)
                    If state.Speed > 150.0 Then blurSamples = 5

                    If blurSamples <= 1 Then
                        ApplyCameraAndCaptureFrame(oDoc, oApp, oCam, tg, state, framePath, settings, renderSnapshot)
                    Else
                        Dim subBitmaps As New List(Of System.Drawing.Bitmap)()
                        Dim shutterDt As Double = (settings.ShutterAngle / 360.0) / CDbl(settings.FPS)
                        Dim dtStart As Double = -0.5 * shutterDt
                        Dim dtStep As Double = shutterDt / CDbl(Math.Max(1, blurSamples - 1))

                        For sampleIndex As Integer = 0 To blurSamples - 1
                            Dim subT As Double = currentT + dtStart + sampleIndex * dtStep
                            subT = Math.Max(0.0, Math.Min(settings.DurationSeconds, subT))

                            Dim subState As CameraState = SampleCameraAtTime(subT, rail, speedLaw, orient, model, heroes, settings)
                            Dim tempSubFile As String = System.IO.Path.Combine(outputDir, "sub_" & sampleIndex.ToString() & ".png")

                            ApplyCameraAndCaptureFrame(oDoc, oApp, oCam, tg, subState, tempSubFile, settings, renderSnapshot)

                            Using fs As New System.IO.FileStream(tempSubFile, System.IO.FileMode.Open, System.IO.FileAccess.Read)
                                subBitmaps.Add(New System.Drawing.Bitmap(fs))
                            End Using
                            Try : System.IO.File.Delete(tempSubFile) : Catch : End Try
                        Next

                        Dim blendedBmp As System.Drawing.Bitmap = BlendBitmapsWeighted(subBitmaps)
                        blendedBmp.Save(framePath, System.Drawing.Imaging.ImageFormat.Png)
                        blendedBmp.Dispose()
                        For Each b As System.Drawing.Bitmap In subBitmaps : b.Dispose() : Next
                    End If

                    frameCountDone += 1
                    oApp.StatusBarText = "WT3D V5.9 Vietnamese Controls: Frame " & frame.ToString() & "/" & settings.TotalFrames.ToString() & " (" & state.ActiveHeroName & ")"
                Next

                If Not aborted AndAlso frameCountDone > 0 Then
                    EncodeVideoWithFFmpeg(outputDir, settings, logPath)
                End If
            End If

        Finally
            ' Never leave the user's assembly altered by a render operation.
            Try : RestoreRenderState(oDoc, renderSnapshot) : Catch : End Try
            Try : oApp.ActiveView.Update() : Catch : End Try
            System.Windows.Forms.Application.DoEvents()
        End Try

        If aborted Then
            MessageBox.Show("Director stopped by user (ESC pressed)." & vbCrLf & _
                            "Original Design View and display visibility have been restored.", _
                            "WT3D WhipCam Studio V5.7", MessageBoxButtons.OK, MessageBoxIcon.Information)
        ElseIf settings.RunMode.StartsWith("EXPORT") Then
            MessageBox.Show("Cinematic V5.9 Vietnamese Controls export completed!" & vbCrLf & _
                            "Video: " & System.IO.Path.Combine(outputDir, "WT3D_Cinematic_V5_9_VietnameseControls.mp4") & vbCrLf & _
                            "Telemetry: " & telemetryCsv, _
                            "WT3D WhipCam Studio V5.7", MessageBoxButtons.OK, MessageBoxIcon.Information)
        End If
    End Sub

    ' --------------------------------------------------------------------------
    ' 13. BENTO STUDIO DIALOG & MAIN LAUNCHER
    ' --------------------------------------------------------------------------
    Public Sub Main()
        Try
            Dim oDoc As Document = ThisDoc.Document
            If oDoc Is Nothing Then
                MessageBox.Show("Please open a part or assembly first!", "WT3D WhipCam V5.9", MessageBoxButtons.OK, MessageBoxIcon.Warning)
                Return
            End If

            Dim oApp As Inventor.Application = ThisApplication
            Dim oCam As Camera = oApp.ActiveView.Camera

            Dim settings As New CameraSettings()

            Dim tips As New System.Windows.Forms.ToolTip()
            tips.AutoPopDelay = 12000
            tips.InitialDelay = 250
            tips.ReshowDelay = 100
            tips.ShowAlways = True

            Dim form As New System.Windows.Forms.Form()
            form.Text = "WT3D WHIPCAM STUDIO V5.9 - DIEU KHIEN CAMERA"
            form.Width = 860
            form.Height = 805
            form.StartPosition = FormStartPosition.CenterScreen
            form.FormBorderStyle = FormBorderStyle.FixedDialog
            form.MaximizeBox = False
            form.MinimizeBox = False
            form.BackColor = System.Drawing.Color.FromArgb(245, 245, 247)
            form.TopMost = True
            form.ShowInTaskbar = True

            Dim lblTitle As New System.Windows.Forms.Label()
            lblTitle.Text = "WT3D WHIPCAM V5.9"
            lblTitle.Font = New System.Drawing.Font("Segoe UI", 14.0!, FontStyle.Bold)
            lblTitle.ForeColor = System.Drawing.Color.FromArgb(27, 122, 62)
            lblTitle.Location = New System.Drawing.Point(20, 15)
            lblTitle.AutoSize = True
            form.Controls.Add(lblTitle)

            Dim lblSub As New System.Windows.Forms.Label()
            lblSub.Text = "Dieu khien truc quan: Xa/Gan · Nhanh/Cham · Orbit · FOV · Nghieng · Motion Blur"
            lblSub.Font = New System.Drawing.Font("Segoe UI", 9.0!, FontStyle.Regular)
            lblSub.ForeColor = System.Drawing.Color.FromArgb(90, 90, 90)
            lblSub.Location = New System.Drawing.Point(22, 45)
            lblSub.AutoSize = True
            form.Controls.Add(lblSub)

            ' ---------------- MODE / OUTPUT ----------------
            Dim grpMode As New System.Windows.Forms.GroupBox()
            grpMode.Text = "XUAT VIDEO / XEM THU"
            grpMode.Location = New System.Drawing.Point(20, 78)
            grpMode.Size = New System.Drawing.Size(360, 155)
            grpMode.BackColor = System.Drawing.Color.White
            grpMode.Font = New System.Drawing.Font("Segoe UI", 9.0!, FontStyle.Bold)
            form.Controls.Add(grpMode)

            Dim rbPreview As New System.Windows.Forms.RadioButton()
            rbPreview.Text = "Xem thu trong Inventor · 30 FPS · GIU ESC de dung"
            rbPreview.Location = New System.Drawing.Point(18, 25)
            rbPreview.Size = New System.Drawing.Size(320, 24)
            rbPreview.Checked = True
            grpMode.Controls.Add(rbPreview)

            Dim rbDraft As New System.Windows.Forms.RadioButton()
            rbDraft.Text = "Xuat nhanh · 720x1280 · 30 FPS"
            rbDraft.Location = New System.Drawing.Point(18, 57)
            rbDraft.Size = New System.Drawing.Size(320, 24)
            grpMode.Controls.Add(rbDraft)

            Dim rbFinal As New System.Windows.Forms.RadioButton()
            rbFinal.Text = "Xuat Master · 1080x1920 · 60 FPS"
            rbFinal.Location = New System.Drawing.Point(18, 89)
            rbFinal.Size = New System.Drawing.Size(320, 24)
            grpMode.Controls.Add(rbFinal)

            Dim lblDur As New System.Windows.Forms.Label()
            lblDur.Text = "Thoi luong (giay)"
            lblDur.Location = New System.Drawing.Point(18, 122)
            lblDur.AutoSize = True
            grpMode.Controls.Add(lblDur)

            Dim numDur As New System.Windows.Forms.NumericUpDown()
            numDur.Location = New System.Drawing.Point(115, 119)
            numDur.Size = New System.Drawing.Size(80, 22)
            numDur.DecimalPlaces = 1
            numDur.Increment = 0.5D
            numDur.Minimum = 3.0D
            numDur.Maximum = 60.0D
            numDur.Value = 10.5D
            grpMode.Controls.Add(numDur)

            ' ---------------- DISTANCE / ORBIT ----------------
            Dim grpDistance As New System.Windows.Forms.GroupBox()
            grpDistance.Text = "KHOANG CACH & DUONG BAY VONG"
            grpDistance.Location = New System.Drawing.Point(400, 78)
            grpDistance.Size = New System.Drawing.Size(380, 260)
            grpDistance.BackColor = System.Drawing.Color.White
            grpDistance.Font = New System.Drawing.Font("Segoe UI", 9.0!, FontStyle.Bold)
            form.Controls.Add(grpDistance)

            Dim lblFar As New System.Windows.Forms.Label() : lblFar.Text = "◎ XA - ban kinh nen (x Hero)" : lblFar.Location = New System.Drawing.Point(18, 30) : lblFar.AutoSize = True : grpDistance.Controls.Add(lblFar)
            Dim numFar As New System.Windows.Forms.NumericUpDown() : numFar.Location = New System.Drawing.Point(230, 27) : numFar.Size = New System.Drawing.Size(105, 22) : numFar.DecimalPlaces = 2 : numFar.Increment = 0.05D : numFar.Minimum = 0.8D : numFar.Maximum = 5.0D : numFar.Value = 2.65D : grpDistance.Controls.Add(numFar)

            Dim lblNear1 As New System.Windows.Forms.Label() : lblNear1.Text = "◉ GAN 1 - lan ap sat dau" : lblNear1.Location = New System.Drawing.Point(18, 65) : lblNear1.AutoSize = True : grpDistance.Controls.Add(lblNear1)
            Dim numNear1 As New System.Windows.Forms.NumericUpDown() : numNear1.Location = New System.Drawing.Point(230, 62) : numNear1.Size = New System.Drawing.Size(105, 22) : numNear1.DecimalPlaces = 2 : numNear1.Increment = 0.05D : numNear1.Minimum = 0.35D : numNear1.Maximum = 4.0D : numNear1.Value = 1.05D : grpDistance.Controls.Add(numNear1)

            Dim lblNear2 As New System.Windows.Forms.Label() : lblNear2.Text = "● GAN 2 - ap sat manh nhat" : lblNear2.Location = New System.Drawing.Point(18, 100) : lblNear2.AutoSize = True : grpDistance.Controls.Add(lblNear2)
            Dim numNear2 As New System.Windows.Forms.NumericUpDown() : numNear2.Location = New System.Drawing.Point(230, 97) : numNear2.Size = New System.Drawing.Size(105, 22) : numNear2.DecimalPlaces = 2 : numNear2.Increment = 0.05D : numNear2.Minimum = 0.30D : numNear2.Maximum = 4.0D : numNear2.Value = 0.62D : grpDistance.Controls.Add(numNear2)

            Dim lblRelease As New System.Windows.Forms.Label() : lblRelease.Text = "↗ Bat xa ra giua 2 lan" : lblRelease.Location = New System.Drawing.Point(18, 135) : lblRelease.AutoSize = True : grpDistance.Controls.Add(lblRelease)
            Dim numRelease As New System.Windows.Forms.NumericUpDown() : numRelease.Location = New System.Drawing.Point(230, 132) : numRelease.Size = New System.Drawing.Size(105, 22) : numRelease.DecimalPlaces = 2 : numRelease.Increment = 0.05D : numRelease.Minimum = 0D : numRelease.Maximum = 1.5D : numRelease.Value = 0.30D : grpDistance.Controls.Add(numRelease)

            Dim lblSweep As New System.Windows.Forms.Label() : lblSweep.Text = "↺ Do quay vong quanh Hero (°)" : lblSweep.Location = New System.Drawing.Point(18, 170) : lblSweep.AutoSize = True : grpDistance.Controls.Add(lblSweep)
            Dim numSweep As New System.Windows.Forms.NumericUpDown() : numSweep.Location = New System.Drawing.Point(230, 167) : numSweep.Size = New System.Drawing.Size(105, 22) : numSweep.DecimalPlaces = 0 : numSweep.Increment = 5D : numSweep.Minimum = 40D : numSweep.Maximum = 320D : numSweep.Value = 190D : grpDistance.Controls.Add(numSweep)

            Dim lblOrganic As New System.Windows.Forms.Label() : lblOrganic.Text = "⌁ Do uon huu co cua cung (°)" : lblOrganic.Location = New System.Drawing.Point(18, 205) : lblOrganic.AutoSize = True : grpDistance.Controls.Add(lblOrganic)
            Dim numOrganic As New System.Windows.Forms.NumericUpDown() : numOrganic.Location = New System.Drawing.Point(230, 202) : numOrganic.Size = New System.Drawing.Size(105, 22) : numOrganic.DecimalPlaces = 1 : numOrganic.Increment = 1D : numOrganic.Minimum = 0D : numOrganic.Maximum = 45D : numOrganic.Value = 5D : grpDistance.Controls.Add(numOrganic)

            ' ---------------- SPEED RHYTHM ----------------
            Dim grpRhythm As New System.Windows.Forms.GroupBox()
            grpRhythm.Text = "NHIP NHANH / CHAM"
            grpRhythm.Location = New System.Drawing.Point(20, 248)
            grpRhythm.Size = New System.Drawing.Size(360, 170)
            grpRhythm.BackColor = System.Drawing.Color.White
            grpRhythm.Font = New System.Drawing.Font("Segoe UI", 9.0!, FontStyle.Bold)
            form.Controls.Add(grpRhythm)

            Dim lblFast As New System.Windows.Forms.Label() : lblFast.Text = "⏩ Lao vao / bay ra nhanh (x)" : lblFast.Location = New System.Drawing.Point(18, 32) : lblFast.AutoSize = True : grpRhythm.Controls.Add(lblFast)
            Dim numFast As New System.Windows.Forms.NumericUpDown() : numFast.Location = New System.Drawing.Point(220, 29) : numFast.Size = New System.Drawing.Size(100, 22) : numFast.DecimalPlaces = 2 : numFast.Increment = 0.1D : numFast.Minimum = 0.35D : numFast.Maximum = 4D : numFast.Value = 1.55D : grpRhythm.Controls.Add(numFast)

            Dim lblHold As New System.Windows.Forms.Label() : lblHold.Text = "⏸ Giu cham khi o GAN (x)" : lblHold.Location = New System.Drawing.Point(18, 70) : lblHold.AutoSize = True : grpRhythm.Controls.Add(lblHold)
            Dim numHold As New System.Windows.Forms.NumericUpDown() : numHold.Location = New System.Drawing.Point(220, 67) : numHold.Size = New System.Drawing.Size(100, 22) : numHold.DecimalPlaces = 2 : numHold.Increment = 0.1D : numHold.Minimum = 0.25D : numHold.Maximum = 4D : numHold.Value = 1.50D : grpRhythm.Controls.Add(numHold)

            Dim lblHoldSpeed As New System.Windows.Forms.Label() : lblHoldSpeed.Text = "▷ Toc do khi dang giu GAN (%)" : lblHoldSpeed.Location = New System.Drawing.Point(18, 108) : lblHoldSpeed.AutoSize = True : grpRhythm.Controls.Add(lblHoldSpeed)
            Dim numHoldSpeed As New System.Windows.Forms.NumericUpDown() : numHoldSpeed.Location = New System.Drawing.Point(220, 105) : numHoldSpeed.Size = New System.Drawing.Size(100, 22) : numHoldSpeed.DecimalPlaces = 0 : numHoldSpeed.Increment = 2D : numHoldSpeed.Minimum = 0D : numHoldSpeed.Maximum = 60D : numHoldSpeed.Value = 9D : grpRhythm.Controls.Add(numHoldSpeed)

            Dim lblHint As New System.Windows.Forms.Label()
            lblHint.Text = "Goi y: Fast 1.4–1.8x + Hold 1.3–1.8x + Hold Speed 6–12% = nhan nhip ro."
            lblHint.Location = New System.Drawing.Point(18, 136)
            lblHint.Size = New System.Drawing.Size(325, 28)
            lblHint.ForeColor = System.Drawing.Color.FromArgb(100, 100, 100)
            lblHint.Font = New System.Drawing.Font("Segoe UI", 8.0!, FontStyle.Italic)
            grpRhythm.Controls.Add(lblHint)

            ' ---------------- VISUAL GUIDE / RECOMMENDED PRESET ----------------
            Dim grpGuide As New System.Windows.Forms.GroupBox()
            grpGuide.Text = "SO DO CHUYEN DONG & PRESET DE XUAT"
            grpGuide.Location = New System.Drawing.Point(20, 435)
            grpGuide.Size = New System.Drawing.Size(360, 250)
            grpGuide.BackColor = System.Drawing.Color.White
            grpGuide.Font = New System.Drawing.Font("Segoe UI", 9.0!, FontStyle.Bold)
            form.Controls.Add(grpGuide)

            Dim lblFlow As New System.Windows.Forms.Label()
            lblFlow.Text = "◎ XA  --NHANH/CUNG-->  ◉ GAN  [GIU]" & vbCrLf & _
                           "   ^                         |" & vbCrLf & _
                           "   |---- NHANH + ORBIT <-----|" & vbCrLf & _
                           "        roi lai lao vao GAN 2"
            lblFlow.Location = New System.Drawing.Point(18, 28)
            lblFlow.Size = New System.Drawing.Size(320, 72)
            lblFlow.Font = New System.Drawing.Font("Consolas", 9.0!, FontStyle.Bold)
            lblFlow.ForeColor = System.Drawing.Color.FromArgb(45, 75, 120)
            grpGuide.Controls.Add(lblFlow)

            Dim lblPreset As New System.Windows.Forms.Label()
            lblPreset.Text = "Preset can bang / de xuat:" & vbCrLf & _
                             "XA 2.65x | GAN1 1.05x | GAN2 0.62x | Orbit 190°" & vbCrLf & _
                             "Fast 1.55x | Hold 1.50x | Hold Speed 9%" & vbCrLf & _
                             "FOV 48° / 62° / 70° | Bank 8.5° | Shutter 180°"
            lblPreset.Location = New System.Drawing.Point(18, 105)
            lblPreset.Size = New System.Drawing.Size(325, 76)
            lblPreset.Font = New System.Drawing.Font("Segoe UI", 8.5!, FontStyle.Regular)
            lblPreset.ForeColor = System.Drawing.Color.FromArgb(75, 75, 75)
            grpGuide.Controls.Add(lblPreset)

            Dim btnPreset As New System.Windows.Forms.Button()
            btnPreset.Text = "★ AP DUNG PRESET DE XUAT"
            btnPreset.Location = New System.Drawing.Point(18, 192)
            btnPreset.Size = New System.Drawing.Size(305, 34)
            btnPreset.BackColor = System.Drawing.Color.FromArgb(235, 246, 238)
            btnPreset.ForeColor = System.Drawing.Color.FromArgb(27, 122, 62)
            btnPreset.FlatStyle = FlatStyle.Flat
            btnPreset.Font = New System.Drawing.Font("Segoe UI", 9.0!, FontStyle.Bold)
            grpGuide.Controls.Add(btnPreset)

            ' ---------------- LENS / BANK / BLUR ----------------
            Dim grpLens As New System.Windows.Forms.GroupBox()
            grpLens.Text = "FOV · NGHIENG CAMERA · MOTION BLUR"
            grpLens.Location = New System.Drawing.Point(400, 353)
            grpLens.Size = New System.Drawing.Size(380, 285)
            grpLens.BackColor = System.Drawing.Color.White
            grpLens.Font = New System.Drawing.Font("Segoe UI", 9.0!, FontStyle.Bold)
            form.Controls.Add(grpLens)

            Dim lblFovFar As New System.Windows.Forms.Label() : lblFovFar.Text = "◌ FOV khi XA / binh thuong" : lblFovFar.Location = New System.Drawing.Point(18, 30) : lblFovFar.AutoSize = True : grpLens.Controls.Add(lblFovFar)
            Dim numFovFar As New System.Windows.Forms.NumericUpDown() : numFovFar.Location = New System.Drawing.Point(230, 27) : numFovFar.Size = New System.Drawing.Size(105, 22) : numFovFar.DecimalPlaces = 0 : numFovFar.Minimum = 20D : numFovFar.Maximum = 100D : numFovFar.Value = 48D : grpLens.Controls.Add(numFovFar)

            Dim lblFovFast As New System.Windows.Forms.Label() : lblFovFast.Text = "≫ FOV khi bay NHANH" : lblFovFast.Location = New System.Drawing.Point(18, 62) : lblFovFast.AutoSize = True : grpLens.Controls.Add(lblFovFast)
            Dim numFovFast As New System.Windows.Forms.NumericUpDown() : numFovFast.Location = New System.Drawing.Point(230, 59) : numFovFast.Size = New System.Drawing.Size(105, 22) : numFovFast.DecimalPlaces = 0 : numFovFast.Minimum = 20D : numFovFast.Maximum = 110D : numFovFast.Value = 62D : grpLens.Controls.Add(numFovFast)

            Dim lblFovNear As New System.Windows.Forms.Label() : lblFovNear.Text = "◉ FOV luc CAN / close-pass" : lblFovNear.Location = New System.Drawing.Point(18, 94) : lblFovNear.AutoSize = True : grpLens.Controls.Add(lblFovNear)
            Dim numFovNear As New System.Windows.Forms.NumericUpDown() : numFovNear.Location = New System.Drawing.Point(230, 91) : numFovNear.Size = New System.Drawing.Size(105, 22) : numFovNear.DecimalPlaces = 0 : numFovNear.Minimum = 20D : numFovNear.Maximum = 110D : numFovNear.Value = 70D : grpLens.Controls.Add(numFovNear)

            Dim lblFovReveal As New System.Windows.Forms.Label() : lblFovReveal.Text = "□ FOV canh ket / reveal" : lblFovReveal.Location = New System.Drawing.Point(18, 126) : lblFovReveal.AutoSize = True : grpLens.Controls.Add(lblFovReveal)
            Dim numFovReveal As New System.Windows.Forms.NumericUpDown() : numFovReveal.Location = New System.Drawing.Point(230, 123) : numFovReveal.Size = New System.Drawing.Size(105, 22) : numFovReveal.DecimalPlaces = 0 : numFovReveal.Minimum = 20D : numFovReveal.Maximum = 100D : numFovReveal.Value = 47D : grpLens.Controls.Add(numFovReveal)

            Dim lblBank As New System.Windows.Forms.Label() : lblBank.Text = "↶ Nghieng khung hinh toi da (°)" : lblBank.Location = New System.Drawing.Point(18, 158) : lblBank.AutoSize = True : grpLens.Controls.Add(lblBank)
            Dim numBank As New System.Windows.Forms.NumericUpDown() : numBank.Location = New System.Drawing.Point(230, 155) : numBank.Size = New System.Drawing.Size(105, 22) : numBank.DecimalPlaces = 1 : numBank.Increment = 0.5D : numBank.Minimum = 0D : numBank.Maximum = 25D : numBank.Value = 8.5D : grpLens.Controls.Add(numBank)

            Dim lblBankGain As New System.Windows.Forms.Label() : lblBankGain.Text = "∿ Do nhay nghieng theo cua (x)" : lblBankGain.Location = New System.Drawing.Point(18, 190) : lblBankGain.AutoSize = True : grpLens.Controls.Add(lblBankGain)
            Dim numBankGain As New System.Windows.Forms.NumericUpDown() : numBankGain.Location = New System.Drawing.Point(230, 187) : numBankGain.Size = New System.Drawing.Size(105, 22) : numBankGain.DecimalPlaces = 2 : numBankGain.Increment = 0.05D : numBankGain.Minimum = 0D : numBankGain.Maximum = 3D : numBankGain.Value = 1.10D : grpLens.Controls.Add(numBankGain)

            Dim chkBlur As New System.Windows.Forms.CheckBox()
            chkBlur.Text = "≈ Bat Motion Blur"
            chkBlur.Location = New System.Drawing.Point(18, 224)
            chkBlur.Size = New System.Drawing.Size(170, 24)
            chkBlur.Checked = True
            grpLens.Controls.Add(chkBlur)

            Dim lblShutter As New System.Windows.Forms.Label() : lblShutter.Text = "Shutter °" : lblShutter.Location = New System.Drawing.Point(195, 227) : lblShutter.AutoSize = True : grpLens.Controls.Add(lblShutter)
            Dim numShutter As New System.Windows.Forms.NumericUpDown() : numShutter.Location = New System.Drawing.Point(270, 224) : numShutter.Size = New System.Drawing.Size(70, 22) : numShutter.DecimalPlaces = 0 : numShutter.Increment = 30D : numShutter.Minimum = 0D : numShutter.Maximum = 360D : numShutter.Value = 180D : grpLens.Controls.Add(numShutter)

            ' Attach preset handler only AFTER all referenced controls are declared.
            AddHandler btnPreset.Click, Sub(sender As Object, e As EventArgs)
                numFar.Value = 2.65D
                numNear1.Value = 1.05D
                numNear2.Value = 0.62D
                numRelease.Value = 0.30D
                numSweep.Value = 190D
                numOrganic.Value = 5D
                numFast.Value = 1.55D
                numHold.Value = 1.50D
                numHoldSpeed.Value = 9D
                numFovFar.Value = 48D
                numFovFast.Value = 62D
                numFovNear.Value = 70D
                numFovReveal.Value = 47D
                numBank.Value = 8.5D
                numBankGain.Value = 1.10D
                chkBlur.Checked = True
                numShutter.Value = 180D
            End Sub

            ' Vietnamese tooltips: explain what changes visually, not just the variable name.
            tips.SetToolTip(numFar, "Khoảng cách nền khi camera ở XA. Tăng số này = toàn cảnh hơn. Khuyên dùng 2.4–3.0x; preset 2.65x.")
            tips.SetToolTip(numNear1, "Khoảng cách cận lần 1. Số nhỏ = camera áp sát hơn. Khuyên dùng 0.95–1.15x.")
            tips.SetToolTip(numNear2, "Cận cảnh mạnh nhất. Chỉ nên rất gần trong thời gian ngắn. Khuyên dùng 0.58–0.75x; preset 0.62x.")
            tips.SetToolTip(numRelease, "Mức camera bật/lùi xa giữa hai lần áp sát. Tăng = nhịp XA/GẦN rõ hơn. Khuyên 0.20–0.40.")
            tips.SetToolTip(numSweep, "Góc camera bay vòng quanh Hero. 180° ≈ nửa vòng. Khuyên 170–210° để vừa tròn vừa không thành tour 360°.")
            tips.SetToolTip(numOrganic, "Độ uốn nhẹ làm quỹ đạo bớt cơ khí. Quá cao dễ rung. Khuyên 3–8°.")
            tips.SetToolTip(numFast, "Độ nhanh khi lao từ XA vào GẦN và khi vọt ra. Khuyên 1.4–1.8x.")
            tips.SetToolTip(numHold, "Kéo dài đoạn chậm/giữ gần Hero để người xem kịp nhìn. Khuyên 1.3–1.8x.")
            tips.SetToolTip(numHoldSpeed, "Tốc độ còn lại khi đang nhấn gần Hero. 0% = gần như dừng. Khuyên 6–12%; preset 9%.")
            tips.SetToolTip(numFovFar, "FOV khi ở xa. FOV nhỏ = khung chặt hơn. Khuyên 46–52°.")
            tips.SetToolTip(numFovFast, "FOV lúc bay nhanh. Tăng FOV tạo cảm giác tốc độ/parallax mạnh hơn. Khuyên 58–65°.")
            tips.SetToolTip(numFovNear, "FOV lúc close-pass. Lưu ý: FOV lớn là góc rộng, KHÔNG phải zoom gần; độ gần đến từ camera di chuyển thật. Khuyên 66–72°.")
            tips.SetToolTip(numFovReveal, "FOV cảnh kết/reveal. Khuyên 45–50° để hình ổn định, ít méo.")
            tips.SetToolTip(numBank, "Góc nghiêng khung hình tối đa khi cua. Quá cao sẽ có cảm giác đảo/lật. Khuyên 7–10°.")
            tips.SetToolTip(numBankGain, "Độ nhạy của banking theo độ cong/tốc độ. Khuyên 0.9–1.3x.")
            tips.SetToolTip(chkBlur, "Motion Blur giúp đoạn bay nhanh mượt hơn, che micro-jitter. Nên bật khi xuất Master.")
            tips.SetToolTip(numShutter, "Shutter angle cho motion blur. 180° là cân bằng; 120–150° nét hơn; 210–240° mờ mạnh hơn.")

            Dim btnOk As New System.Windows.Forms.Button()
            btnOk.Text = "▶ CHAY CAMERA"
            btnOk.Location = New System.Drawing.Point(555, 710)
            btnOk.Size = New System.Drawing.Size(140, 38)
            btnOk.BackColor = System.Drawing.Color.FromArgb(27, 122, 62)
            btnOk.ForeColor = System.Drawing.Color.White
            btnOk.FlatStyle = FlatStyle.Flat
            btnOk.Font = New System.Drawing.Font("Segoe UI", 10.0!, FontStyle.Bold)
            btnOk.DialogResult = DialogResult.OK
            form.Controls.Add(btnOk)

            Dim btnCancel As New System.Windows.Forms.Button()
            btnCancel.Text = "HUY"
            btnCancel.Location = New System.Drawing.Point(705, 710)
            btnCancel.Size = New System.Drawing.Size(90, 38)
            btnCancel.BackColor = System.Drawing.Color.FromArgb(220, 220, 220)
            btnCancel.FlatStyle = FlatStyle.Flat
            btnCancel.DialogResult = DialogResult.Cancel
            form.Controls.Add(btnCancel)

            AddHandler btnOk.Click, Sub(sender As Object, e As EventArgs) form.Close()
            AddHandler btnCancel.Click, Sub(sender As Object, e As EventArgs) form.Close()

            form.BringToFront()
            form.Activate()

            If form.ShowDialog() = DialogResult.OK Then
                settings.DurationSeconds = CDbl(numDur.Value)

                settings.FarDistanceScale = CDbl(numFar.Value)
                settings.Near1DistanceScale = CDbl(numNear1.Value)
                settings.Near2DistanceScale = CDbl(numNear2.Value)
                settings.ReleaseDistanceBoost = CDbl(numRelease.Value)
                settings.OrbitSweepDegrees = CDbl(numSweep.Value)
                settings.OrbitOrganicBiasDegrees = CDbl(numOrganic.Value)

                settings.FastSpeedMultiplier = CDbl(numFast.Value)
                settings.NearHoldMultiplier = CDbl(numHold.Value)
                settings.NearHoldSpeedPercent = CDbl(numHoldSpeed.Value)

                settings.FOVFarDegrees = CDbl(numFovFar.Value)
                settings.FOVFastDegrees = CDbl(numFovFast.Value)
                settings.FOVNearDegrees = CDbl(numFovNear.Value)
                settings.FOVRevealDegrees = CDbl(numFovReveal.Value)
                settings.MaxBankDegrees = CDbl(numBank.Value)
                settings.BankGainMultiplier = CDbl(numBankGain.Value)

                settings.EnableMotionBlur = chkBlur.Checked
                settings.ShutterAngle = CDbl(numShutter.Value)

                If rbPreview.Checked Then
                    settings.RunMode = "PREVIEW"
                    settings.FPS = 30
                    settings.TotalFrames = CInt(settings.DurationSeconds * settings.FPS)
                ElseIf rbDraft.Checked Then
                    settings.RunMode = "EXPORT_DRAFT"
                    settings.FPS = 30
                    settings.Width = 720
                    settings.Height = 1280
                    settings.EnableMotionBlur = False
                    settings.TotalFrames = CInt(settings.DurationSeconds * settings.FPS)
                ElseIf rbFinal.Checked Then
                    settings.RunMode = "EXPORT_FINAL"
                    settings.FPS = 60
                    settings.Width = 1080
                    settings.Height = 1920
                    settings.TotalFrames = CInt(settings.DurationSeconds * settings.FPS)
                End If

                ExecuteDirector(oDoc, oCam, settings)
            End If
        Catch ex As Exception
            MessageBox.Show("WT3D Camera Error: " & ex.Message & vbCrLf & ex.StackTrace, "WT3D Error", MessageBoxButtons.OK, MessageBoxIcon.Error)
        End Try
    End Sub

End Class
