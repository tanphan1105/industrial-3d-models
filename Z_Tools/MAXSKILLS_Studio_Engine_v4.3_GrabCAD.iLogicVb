AddReference "PresentationCore"
AddReference "WindowsBase"
AddReference "System.Drawing"
AddReference "System.Private.Windows.GdiPlus"
AddReference "System.Windows.Forms"
AddReference "System.Private.Windows.Core"

Imports System.Windows.Input
Imports System
Imports System.IO
Imports System.Collections.Generic
Imports Inventor
Imports System.Windows.Forms

' ==============================================================================

' MAXSKILLS 4.3 — BUYER PSYCHOLOGY AI DIRECTOR

' Author: Mr Tấn

' Level: HOLLYWOOD × B2B × INDUSTRIAL SALES

'

' CORE PHILOSOPHY:

' - Quay để BÁN, không quay để khoe

' - AI không chỉ nhìn HÌNH, mà hiểu NGƯỜI XEM

' - Mỗi góc máy đều có "lý do tâm lý"

'

' ==============================================================================

' 0. GLOBAL CONCEPT

' ------------------------------------------------------------------------------

' AI Director = Geometry Intelligence

'             + Functional Semantics

'             + Buyer Psychology

'             + Commercial Intent

'

' Không có shot "cho đẹp".

' Mỗi shot phải trả lời 1 câu hỏi của khách hàng:

'   - Nó to cỡ nào?

'   - Nó có đáng tin không?

'   - Nó làm việc ra sao?

'   - Tôi có nên trả tiền cho nó không?

' ==============================================================================









Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

        Public Sub Main()

            Dim oDoc As Document = ThisDoc.Document

            Dim baseName As String = System.IO.Path.GetFileNameWithoutExtension(oDoc.FullFileName)

            ThisApplication.StatusBarText = "[MAXSKILLS 4.3 Psychology] Phân tích người mua: " & baseName



            ' ==============================================

            ' 1. Trí tuệ Phân loại Tâm Lý (SmartClassifyAI_43)

            ' ==============================================

            Dim shapeClass As String = ""

            Dim funcClass As String = ""

            Dim vWeight As String = ""

            Dim buyerPersona As String = ""

            SmartClassifyAI_43(oDoc, shapeClass, funcClass, vWeight, buyerPersona)



            Dim commercialIntent As String = "Hero_Product" 



            ThisApplication.StatusBarText = "[MAXSKILLS 4.3] Persona: " & buyerPersona & " | Weight: " & vWeight & " | Shape: " & shapeClass



            ' ==============================================

            ' 2. AI Director Decision Tree (Lập kịch bản)

            ' ==============================================

            Dim cameraPresets As List(Of String) = SelectCinematicCameraAI_43(shapeClass, funcClass, vWeight, buyerPersona, commercialIntent)



            ' ==============================================

            ' 3. THIẾT LẬP MÔI TRƯỜNG QUAY

            ' ==============================================

            Dim oView As Inventor.View = ThisApplication.ActiveView

            Dim oCam As Inventor.Camera = oView.Camera



            Try

                oView.DisplayMode = DisplayModeEnum.kShadedWithEdgesRendering

                oView.Update()

                ThisApplication.ColorSchemes.BackgroundType = BackgroundTypeEnum.kGradientBackgroundType

                Try

                    oDoc.ActiveLightingStyle = oDoc.LightingStyles.Item("Photo Booth")

                Catch

                    Try : oDoc.ActiveLightingStyle = oDoc.LightingStyles.Item("Empty Lab") : Catch : End Try

                End Try

                oView.ShowGroundShadows = True

                oView.ShowAmbientShadows = True

                oView.ShowObjectShadows = True



                ' Tự động dọn rác khung hình (Tắt hêt Mặt phẳng, Trục, Điểm, Sketch thừa)

                Try

                    oDoc.ObjectVisibility.AllWorkFeatures = False

                    oDoc.ObjectVisibility.Sketches = False

                    oDoc.ObjectVisibility.WeldmentSymbols = False

                Catch : End Try

            Catch : End Try



            oCam.Perspective = True



            Dim cX As Double = 0, cY As Double = 0, cZ As Double = 0

            Dim maxDim As Double = 100

            Dim dx As Double = 100, dy As Double = 100, dz As Double = 100



            If oDoc.DocumentType = DocumentTypeEnum.kAssemblyDocumentObject Then

                Dim oAsm As AssemblyDocument = CType(oDoc, AssemblyDocument)

                Dim rB As Box = oAsm.ComponentDefinition.RangeBox

                dx = rB.MaxPoint.X - rB.MinPoint.X

                dy = rB.MaxPoint.Y - rB.MinPoint.Y

                dz = rB.MaxPoint.Z - rB.MinPoint.Z

                cX = rB.MinPoint.X + dx / 2

                cY = rB.MinPoint.Y + dy * 0.4

                cZ = rB.MinPoint.Z + dz / 2

                maxDim = Math.Max(dx, Math.Max(dy, dz))

            End If



            ' ==============================================

            ' 4. THỰC THI QUAY PHIM

            ' ==============================================

            Dim exportDir As String = "d:\WT3D_Project\1_Exports_Batch\" & baseName & "\NIGHTCRAWLER_V43"

            If Not System.IO.Directory.Exists(exportDir) Then System.IO.Directory.CreateDirectory(exportDir)

            For Each f In System.IO.Directory.GetFiles(exportDir, "*.png")

                Try : System.IO.File.Delete(f) : Catch : End Try

            Next



            Dim tg As TransientGeometry = ThisApplication.TransientGeometry



            ' ==============================================

            ' 3.5 BẮT BUỘC CHUẨN HÓA CAMERA TRƯỚC KHI QUAY

            ' Ép phần mềm quên đi mức Zoom bằng tay của Sếp trước đó

            ' ==============================================

            oCam.Perspective = True

            oCam.Target = tg.CreatePoint(cX, cY, cZ)

            oCam.UpVector = tg.CreateUnitVector(0, 1, 0)

            oCam.ViewOrientationType = ViewOrientationTypeEnum.kIsoTopRightViewOrientation

            oCam.Fit()

            Dim initExtW, initExtH As Double

            oCam.GetExtents(initExtW, initExtH)

            oCam.SetExtents(initExtW * 1.05, initExtH * 1.05) ' Lock an toàn 16:9

            oCam.ApplyWithoutTransition()



            Dim fc As Integer = 1



            For Each shotType As String In cameraPresets

                ThisApplication.StatusBarText = "[AI Director 4.3/" & buyerPersona & "] " & shotType



                Select Case shotType

                    ' -------------------------------------------------------------

                    ' ESTABLISHING & EMOTION

                    ' -------------------------------------------------------------

                    Case "Orbit_Majestic" ' Uy quyền (Investor)

                        For i As Integer = 1 To 45

                            Dim t As Double = i / 45.0

                            Dim eT As Double = 3*Math.Pow(t,2) - 2*Math.Pow(t,3) 

                            Dim theta As Double = Math.PI * 1.5 * Math.Pow(t, 1.2) ' Tăng tốc độ bay vòng 1.5x

                            Dim curR As Double = maxDim * 2.0

                            oCam.Eye = tg.CreatePoint(cX + curR * Math.Cos(theta), cY + maxDim * 0.4, cZ + curR * Math.Sin(theta))

                            oCam.Target = tg.CreatePoint(cX, cY + maxDim * 0.1, cZ)

                            oCam.UpVector = tg.CreateUnitVector(0, 1, 0)

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    Case "Dolly_Vertigo" ' Giá trị hệ thống lớn

                        Dim baseAngleVer As Double = oCam.PerspectiveAngle

                        For i As Integer = 1 To 30

                            Dim t As Double = i / 30.0

                            Dim eT As Double = Math.Pow(t, 0.4) 

                            Dim curR As Double = maxDim * (1.1 + 1.2 * eT)

                            oCam.Eye = tg.CreatePoint(cX + curR * Math.Cos(Math.PI*1.5), cY + maxDim * 0.1, cZ + curR * Math.Sin(Math.PI*1.5))

                            oCam.Target = tg.CreatePoint(cX, cY, cZ)

                            oCam.UpVector = tg.CreateUnitVector(0, 1, 0)

                            Try : oCam.PerspectiveAngle = baseAngleVer * (1 - 0.4 * eT) : Catch : End Try

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next

                        Try : oCam.PerspectiveAngle = baseAngleVer : Catch : End Try



                    Case "Extents_Pullback_Reveal" ' Đòn tâm lý kích thích tò mò (Thế chỗ Crane Descent phần ngực máy)

                        ' Bắt đầu khung nhìn cận cảnh nhỏ (40% bề ngang) ngay trung tâm ngực máy, sau đó lùi giãn ra toàn máy

                        Dim startExtW As Double = maxDim * 0.4 

                        Dim endExtW As Double = initExtW * 1.05

                        Dim startExtH As Double = startExtW * (initExtH / initExtW)

                        Dim endExtH As Double = initExtH * 1.05



                        oCam.Eye = tg.CreatePoint(cX + maxDim*1.2 * Math.Cos(Math.PI*0.25), cY + maxDim * 0.2, cZ + maxDim*1.2 * Math.Sin(Math.PI*0.25))

                        oCam.Target = tg.CreatePoint(cX, cY, cZ)

                        oCam.UpVector = tg.CreateUnitVector(0, 1, 0)



                        For i As Integer = 1 To 45 ' Trải dàiiii hơn tí để lấy đà

                            Dim t As Double = i / 45.0

                            Dim eT As Double = 1.0 - Math.Pow(1.0 - t, 3.0) ' Ease Out mượt mà

                            oCam.SetExtents(startExtW + (endExtW - startExtW) * eT, startExtH + (endExtH - startExtH) * eT)

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next

                        ' Trả lại extents để các shot sau không bị ảo

                        oCam.SetExtents(initExtW * 1.05, initExtH * 1.05)



                    Case "Crane_Descent"  ' Quy mô bối cảnh bao quát

                        For i As Integer = 1 To 30

                            Dim t As Double = i / 30.0

                            Dim curY As Double = cY + maxDim * (2.2 - 1.6 * t) ' Rơi nhanh sâu hơn để ép nhịp mào đầu

                            oCam.Eye = tg.CreatePoint(cX + maxDim*1.0, curY, cZ + maxDim*1.0)

                            oCam.Target = tg.CreatePoint(cX, cY, cZ)

                            oCam.UpVector = tg.CreateUnitVector(0, 1, 0)

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    Case "Dutch_Zoom_Twist"  ' Đòn tâm lý Tension (Vẫn giữ thẳng trục Y theo chuẩn 4.1 để tránh nghiêng tháp)

                        For i As Integer = 1 To 20

                            Dim t As Double = i / 20.0

                            Dim curR As Double = maxDim * (0.8 + 1.2 * t)

                            oCam.Eye = tg.CreatePoint(cX + curR * Math.Cos(Math.PI*1.2), cY + maxDim*0.2, cZ + curR * Math.Sin(Math.PI*1.2))

                            oCam.Target = tg.CreatePoint(cX, cY, cZ)

                            oCam.UpVector = tg.CreateUnitVector(0, 1, 0) ' LUÔN GIỮ THẲNG

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    Case "Top_Down_God_Eye"  ' Kiểm soát toàn cục

                        For i As Integer = 1 To 20

                            Dim t As Double = i / 20.0

                            Dim curY As Double = cY + maxDim * (1.8 - 0.4 * t)

                            oCam.Eye = tg.CreatePoint(cX + 0.01, curY, cZ) 

                            oCam.Target = tg.CreatePoint(cX, cY, cZ)

                            oCam.UpVector = tg.CreateUnitVector(0, 0, -1) ' KHÔNG SPIN

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    ' -------------------------------------------------------------

                    ' ENGINEER / PROCESS SHOTS

                    ' -------------------------------------------------------------

                    Case "Flowline_Track" ' Logic Vận hành

                        For i As Integer = 1 To 45

                            Dim t As Double = i / 45.0

                            Dim eT As Double = t ' Tuyến tính

                            Dim isZFlat As Boolean = (dz > dx)

                            Dim theta As Double = Math.PI * 0.4 + (Math.PI * 0.25) * eT ' Quay vòng cung Parallax nhanh hơn

                            If isZFlat Then

                                oCam.Eye = tg.CreatePoint(cX + maxDim*1.2 * Math.Sin(theta), cY + maxDim*0.3, cZ + maxDim*1.2 * Math.Cos(theta))

                                oCam.Target = tg.CreatePoint(cX, cY, cZ)

                            Else

                                oCam.Eye = tg.CreatePoint(cX + maxDim*1.2 * Math.Cos(theta), cY + maxDim*0.3, cZ + maxDim*1.2 * Math.Sin(theta))

                                oCam.Target = tg.CreatePoint(cX, cY, cZ)

                            End If

                            oCam.UpVector = tg.CreateUnitVector(0, 1, 0)

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    Case "Energy_Path_Reveal" ' Dòng năng lượng

                        For i As Integer = 1 To 30

                            Dim t As Double = i / 30.0

                            Dim eT As Double = t ' Chuyển tuyến tính

                            Dim isZFlat As Boolean = (dz > dx)

                            Dim theta As Double = Math.PI * 0.2 + (Math.PI * 0.25) * eT ' Tốc độ quay vòng nhanh hơn

                            If isZFlat Then

                                oCam.Eye = tg.CreatePoint(cX + maxDim*1.0 * Math.Sin(theta), cY - maxDim*0.2, cZ + maxDim*1.0 * Math.Cos(theta))

                                oCam.Target = tg.CreatePoint(cX, cY + maxDim*0.1, cZ)

                            Else

                                oCam.Eye = tg.CreatePoint(cX + maxDim*1.0 * Math.Cos(theta), cY - maxDim*0.2, cZ + maxDim*1.0 * Math.Sin(theta))

                                oCam.Target = tg.CreatePoint(cX, cY + maxDim*0.1, cZ)

                            End If

                            oCam.UpVector = tg.CreateUnitVector(0, 1, 0)

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    Case "Low_Tracking_Sneak"  ' Thực tế cấu trúc chân đế

                        For i As Integer = 1 To 30

                            Dim t As Double = i / 30.0

                            Dim eT As Double = t ' Linear

                            Dim theta As Double = Math.PI * 0.4 + (Math.PI * 0.3) * eT ' Lướt ngang quét nhanh gầm

                            oCam.Eye = tg.CreatePoint(cX + maxDim*1.2 * Math.Cos(theta), cY - maxDim*0.3, cZ + maxDim*1.2 * Math.Sin(theta))

                            oCam.Target = tg.CreatePoint(cX, cY + maxDim*0.2, cZ)

                            oCam.UpVector = tg.CreateUnitVector(0, 1, 0)

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    Case "Exploded_Dive" ' (Motion Proof) Lao cực sâu phanh gấp

                        Dim baseAngleExp As Double = oCam.PerspectiveAngle

                        For i As Integer = 1 To 15

                            Dim t As Double = i / 15.0

                            Dim eT As Double = Math.Pow(t, 2.0)

                            Dim curR As Double = maxDim * (2.0 - 1.2 * eT) ' Phanh gấp an toàn ở cự ly 0.8x chống nổ xuyên hình

                            oCam.Eye = tg.CreatePoint(cX + curR * Math.Cos(Math.PI), cY - maxDim * 0.05, cZ + curR * Math.Sin(Math.PI))

                            oCam.Target = tg.CreatePoint(cX, cY + maxDim * 0.2, cZ)

                            oCam.UpVector = tg.CreateUnitVector(0, 1, 0)

                            Try : oCam.PerspectiveAngle = baseAngleExp * (1 + 0.3 * eT) : Catch : End Try

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next

                        Try : oCam.PerspectiveAngle = baseAngleExp : Catch : End Try



                    Case "Fit_To_View_Finale" ' (Signature SEO Shot) Trượt mượt thần tốc về góc ViewCube

                        ' 1. Bắt dính trạng thái Camera

                        Dim startEye As Inventor.Point = oCam.Eye.Copy()

                        Dim startTarget As Inventor.Point = oCam.Target.Copy()

                        Dim startUpVector As Inventor.UnitVector = oCam.UpVector.Copy()

                        Dim startExtW As Double, startExtH As Double

                        oCam.GetExtents(startExtW, startExtH)



                        ' 2. Lấy tham số Đích (Perfect Iso Home)

                        oCam.Target = tg.CreatePoint(cX, cY, cZ)

                        oCam.UpVector = tg.CreateUnitVector(0, 1, 0)

                        oCam.ViewOrientationType = ViewOrientationTypeEnum.kIsoTopRightViewOrientation

                        oCam.Fit()

                        Dim endEye As Inventor.Point = oCam.Eye.Copy()

                        Dim endTarget As Inventor.Point = oCam.Target.Copy()

                        Dim endUpVector As Inventor.UnitVector = oCam.UpVector.Copy()

                        Dim endExtW As Double, endExtH As Double

                        oCam.GetExtents(endExtW, endExtH)

                        endExtW = endExtW * 1.05 ' Margin 16:9

                        endExtH = endExtH * 1.05



                        ' 3. Vòng lặp Nội suy (Linear Interpolation Lerp + Ease Out Cubic) tốc độ cao

                        Dim transFrames As Integer = 30 ' 1.0 giây quay cua gấp lấy lại thăng bằng

                        For i As Integer = 1 To transFrames

                            Dim t As Double = i / CDbl(transFrames)

                            Dim eT As Double = 1.0 - Math.Pow(1.0 - t, 3.0) 



                            oCam.Eye = tg.CreatePoint(startEye.X + (endEye.X - startEye.X) * eT, startEye.Y + (endEye.Y - startEye.Y) * eT, startEye.Z + (endEye.Z - startEye.Z) * eT)

                            oCam.Target = tg.CreatePoint(startTarget.X + (endTarget.X - startTarget.X) * eT, startTarget.Y + (endTarget.Y - startTarget.Y) * eT, startTarget.Z + (endTarget.Z - startTarget.Z) * eT)

                            oCam.UpVector = tg.CreateUnitVector(startUpVector.X + (endUpVector.X - startUpVector.X) * eT, startUpVector.Y + (endUpVector.Y - startUpVector.Y) * eT, startUpVector.Z + (endUpVector.Z - startUpVector.Z) * eT)

                            oCam.SetExtents(startExtW + (endExtW - startExtW) * eT, startExtH + (endExtH - startExtH) * eT)



                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                        ' 4. THUẬT TOÁN ĐÓNG BĂNG GIỜ VÀNG (11 GIÂY CHUẨN SEO CHO BẢN KỸ SƯ 4.3)

                        ' Lấp đầy biến số Thời gian: Tự động đo lường khoảnh khắc hụt và niêm phong Video ở mốc 330 frames (11s)

                        Dim freezeFrames As Integer = 330 - fc + 1

                        If freezeFrames < 15 Then freezeFrames = 15 ' Cầu chì: NEO tối thiểu 0.5 giây



                        For i As Integer = 1 To freezeFrames

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    ' -------------------------------------------------------------

                    ' SAFETY / RELIABILITY SHOTS

                    ' -------------------------------------------------------------

                    Case "Monument_Lift" ' Hiện tháp tượng đài độ dày

                        Dim startY As Double = cY - dy * 0.6 ' Hạ thấp hơn

                        Dim endY As Double = cY + dy * 0.8 ' Thốc cao hơn

                        Dim baseFOV As Double = oCam.PerspectiveAngle

                        For i As Integer = 1 To 45

                            Dim t As Double = i / 45.0

                            Dim eT As Double = Math.Pow(t, 2.0)

                            oCam.Eye = tg.CreatePoint(cX + maxDim*1.2, startY + (endY - startY)*eT, cZ + maxDim*0.5)

                            oCam.Target = tg.CreatePoint(cX, startY + (endY - startY)*eT + maxDim*0.2, cZ)

                            oCam.UpVector = tg.CreateUnitVector(0, 1, 0)

                            Try : oCam.PerspectiveAngle = baseFOV * (1 + 0.3 * eT) : Catch : End Try

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next

                        Try : oCam.PerspectiveAngle = baseFOV : Catch : End Try



                    Case "Worm_Eye_Whip" ' Vững chãi

                        For i As Integer = 1 To 10

                            Dim t As Double = i / 10.0

                            Dim theta As Double = Math.PI * 1.2 + (Math.PI / 3.0) * Math.Pow(t, 2.0)

                            oCam.Eye = tg.CreatePoint(cX + maxDim*1.2 * Math.Cos(theta), cY - dy * 0.4, cZ + maxDim*1.2 * Math.Sin(theta))

                            oCam.Target = tg.CreatePoint(cX, cY + maxDim * 0.4, cZ) 

                            oCam.UpVector = tg.CreateUnitVector(0, 1, 0) 

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    Case "Axis_Reveal" ' Mép và khối thép

                        For i As Integer = 1 To 30

                            Dim t As Double = i / 30.0

                            Dim theta As Double = Math.PI * 0.25 * t

                            Dim Rr As Double = maxDim * 0.8

                            oCam.Eye = tg.CreatePoint(cX + Rr * Math.Cos(theta), cY + dy*0.2, cZ + Rr * Math.Sin(theta))

                            oCam.Target = tg.CreatePoint(cX, cY, cZ)

                            oCam.UpVector = tg.CreateUnitVector(0, 1, 0)

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    ' -------------------------------------------------------------

                    ' TECHNICIAN / DETAIL SHOTS

                    ' -------------------------------------------------------------

                    Case "Material_Kiss" ' Bề mặt gia công

                        For i As Integer = 1 To 20

                            Dim t As Double = i / 20.0

                            Dim eT As Double = Math.Pow(t, 2.0)

                            Dim curR As Double = Math.Max(dx, dz) / 2.0 + maxDim * 0.2 ' Vá lỗi cự ly an toàn mép ngoài cụm máy

                            Dim theta As Double = Math.PI * 0.25 + (Math.PI * 0.1) * eT 

                            oCam.Eye = tg.CreatePoint(cX + curR * Math.Cos(theta), cY + maxDim * (0.05 + 0.15*eT), cZ + curR * Math.Sin(theta))

                            oCam.Target = tg.CreatePoint(cX, cY, cZ)

                            oCam.UpVector = tg.CreateUnitVector(0, 1, 0)

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                    Case "Precision_Lock" ' Chuẩn kỹ thuật

                        For i As Integer = 1 To 10

                            Dim t As Double = i / 10.0

                            Dim curR As Double = maxDim * (1.2 - 0.5 * t) ' Dừng đúng tầm an toàn 0.7x

                            oCam.Eye = tg.CreatePoint(cX + curR, cY + maxDim*0.2, cZ + curR)

                            oCam.Target = tg.CreatePoint(cX, cY - maxDim*0.1, cZ)

                            oCam.UpVector = tg.CreateUnitVector(0, 1, 0)

                            oCam.ApplyWithoutTransition() : oCam.SaveAsBitmap(exportDir & "\frame_" & fc.ToString("000") & ".png", 2560, 1440) : fc += 1



                If CheckEscape() Then
                    ThisApplication.StatusBarText = "🛑 ĐÃ DỪNG TIẾN TRÌNH THEO LỆNH (GIỮ PHÍM ESC)!"
                    Exit Sub
                End If
                SafeYield(20)
                        Next



                End Select

            Next



            ' Trạm kết xuất FFmpeg

            Dim ps1Path As String = "d:\WT3D_Project\Z_Tools\Auto_Stitch_Video.ps1"

            If System.IO.File.Exists(ps1Path) Then

                Dim processLine As String = "powershell.exe -ExecutionPolicy Bypass -WindowStyle Hidden -File """ & ps1Path & """ -TargetFolder """ & exportDir & """"

                Shell(processLine, vbNormalFocus)

            End If

            ThisApplication.StatusBarText = "[MAXSKILLS 4.3 AI] DONE! Trạm FFmpeg đang xuất MP4 theo chuẩn Seller..."

        End Sub



        ' ==============================================================================

        ' 1. SMART CLASSIFY AI 4.3 (NGỮ NGHĨA + TÂM LÝ)

        ' ==============================================================================

        Sub SmartClassifyAI_43(oDoc As Document, _
                               ByRef shapeClass As String, _
                               ByRef funcClass As String, _
                               ByRef vWeight As String, _
                               ByRef buyerPersona As String)



            ' -------------------------------

            ' DEFAULT

            ' -------------------------------

            shapeClass = "Compact"

            funcClass = "General_Part"

            vWeight = "Light"

            buyerPersona = "Engineer"



            Dim nameL As String = oDoc.DisplayName.ToLower()



            ' -------------------------------

            ' FUNCTIONAL SEMANTIC

            ' -------------------------------

            If nameL.Contains("pump") Or nameL.Contains("bơm") Then funcClass = "Control_Component"

            If nameL.Contains("valve") Or nameL.Contains("van") Then funcClass = "Control_Component"

            If nameL.Contains("sensor") Or nameL.Contains("cảm biến") Then funcClass = "Instrumentation"

            If nameL.Contains("ro") Or nameL.Contains("membrane") Then funcClass = "Process_Core"

            If nameL.Contains("skid") Or nameL.Contains("system") Then funcClass = "System_Core"

            If nameL.Contains("tank") Or nameL.Contains("filter") Or nameL.Contains("bồn") Then funcClass = "Pressure_Vessel"



            ' -------------------------------

            ' GEOMETRY ANALYSIS

            ' -------------------------------

            If oDoc.DocumentType = DocumentTypeEnum.kAssemblyDocumentObject Then

                Dim asm As AssemblyDocument = CType(oDoc, AssemblyDocument)

                Dim rB As Box = asm.ComponentDefinition.RangeBox



                Dim dx As Double = rB.MaxPoint.X - rB.MinPoint.X

                Dim dy As Double = rB.MaxPoint.Y - rB.MinPoint.Y

                Dim dz As Double = rB.MaxPoint.Z - rB.MinPoint.Z



                Dim partCount As Integer = asm.ComponentDefinition.Occurrences.AllLeafOccurrences.Count



                ' Shape

                If dy > 1.8 * Math.Max(dx, dz) Then

                    shapeClass = "Tall"

                ElseIf Math.Max(dx, dz) > 2.0 * dy Then

                    shapeClass = "Flat"

                Else

                    shapeClass = "Compact"

                End If



                ' Visual Weight

                If partCount > 60 Or funcClass = "System_Core" Then

                    vWeight = "Heavy"

                ElseIf partCount > 25 Then

                    vWeight = "Medium"

                End If



                If funcClass = "Pressure_Vessel" Then vWeight = "Heavy"

            End If



            ' -------------------------------

            ' BUYER PERSONA INFERENCE

            ' -------------------------------

            Select Case funcClass

                Case "System_Core"

                    buyerPersona = "Investor"       ' nhìn tổng thể – uy lực – quy mô

                Case "Process_Core"

                    buyerPersona = "Engineer"       ' logic – dòng chảy – hiệu suất

                Case "Pressure_Vessel"

                    buyerPersona = "Safety_Manager" ' độ dày – ổn định – đáng tin

                Case "Control_Component"

                    buyerPersona = "Technician"     ' chi tiết – gia công – lắp đặt

                Case Else

                    buyerPersona = "Engineer"

            End Select

        End Sub



        ' ==============================================================================

        ' 2. AI DIRECTOR 4.3 — DECISION TREE

        ' ==============================================================================

        Function SelectCinematicCameraAI_43(shapeClass As String, _
                                            funcClass As String, _
                                            vWeight As String, _
                                            buyerPersona As String, _
                                            intent As String) As List(Of String)



            Dim shots As New List(Of String)



            ' --------------------------------------------------------------------------

            ' HERO PRODUCT — VIDEO BÁN HÀNG CHỦ LỰC (ALL PATHS EXPANDED TO ~10 SECONDS MOVEMENT)

            ' --------------------------------------------------------------------------

            If intent = "Hero_Product" Then



                ' ===============================

                ' INVESTOR / OWNER MINDSET (Mật độ 295 Frames di chuyển)

                ' ===============================

                If buyerPersona = "Investor" Then

                    shots.Add("Extents_Pullback_Reveal") ' 45f (Kéo dài khung cảnh)

                    shots.Add("Monument_Lift")          ' 45f (Tượng đài uy nghi)

                    shots.Add("Orbit_Majestic")         ' 45f (Quy hoàn Vũ trụ)

                    shots.Add("Crane_Descent")          ' 30f (Góc máy cẩu xoăy)

                    shots.Add("Dolly_Vertigo")          ' 30f (Đòn Giá trị siêu căng)

                    shots.Add("Top_Down_God_Eye")       ' 20f (Quyền lực tuyệt đối)

                    shots.Add("Dutch_Zoom_Twist")       ' 20f (Góc nghiêng kịch tính)

                    shots.Add("Energy_Path_Reveal")     ' 30f (Mạch sống)

                    shots.Add("Fit_To_View_Finale")



                ' ===============================

                ' ENGINEER / PROCESS MINDSET (Mật độ 290 Frames di chuyển)

                ' ===============================

                ElseIf buyerPersona = "Engineer" Then

                    shots.Add("Extents_Pullback_Reveal") ' 45f (Mở bát định hình)

                    shots.Add("Flowline_Track")         ' 45f (Chạy đua dòng lưu chất)

                    shots.Add("Orbit_Majestic")         ' 45f (Soi toàn bộ kết cấu)

                    shots.Add("Energy_Path_Reveal")     ' 30f (Luồng năng lượng chéo)

                    shots.Add("Low_Tracking_Sneak")     ' 30f (Canh gầm máy sát đất)

                    shots.Add("Axis_Reveal")            ' 30f (Xoay mép gia công)

                    shots.Add("Exploded_Dive")          ' 15f (Phanh gấp lặn sâu cấu trúc)

                    shots.Add("Precision_Lock")         ' 10f (Chuẩn ren kỹ thuật)

                    shots.Add("Material_Kiss")          ' 20f (Hôn bề mặt Inox)

                    shots.Add("Top_Down_God_Eye")       ' 20f (Đọc bản vẽ mặt bằng)

                    shots.Add("Fit_To_View_Finale")



                ' ===============================

                ' SAFETY / RELIABILITY MINDSET (Mật độ 285 Frames di chuyển)

                ' ===============================

                ElseIf buyerPersona = "Safety_Manager" Then

                    shots.Add("Extents_Pullback_Reveal")

                    shots.Add("Orbit_Majestic")         

                    shots.Add("Low_Tracking_Sneak")     

                    shots.Add("Monument_Lift")          

                    shots.Add("Worm_Eye_Whip")          

                    shots.Add("Axis_Reveal")            

                    shots.Add("Material_Kiss")          

                    shots.Add("Top_Down_God_Eye")       

                    shots.Add("Precision_Lock")         

                    shots.Add("Fit_To_View_Finale")



                ' ===============================

                ' TECHNICIAN / DETAIL MINDSET (Mật độ 290 Frames di chuyển)

                ' ===============================

                ElseIf buyerPersona = "Technician" Then

                    shots.Add("Extents_Pullback_Reveal")

                    shots.Add("Axis_Reveal")            

                    shots.Add("Low_Tracking_Sneak")     

                    shots.Add("Orbit_Majestic")         

                    shots.Add("Material_Kiss")          

                    shots.Add("Precision_Lock")         

                    shots.Add("Exploded_Dive")          

                    shots.Add("Flowline_Track")         

                    shots.Add("Dutch_Zoom_Twist")

                    shots.Add("Fit_To_View_Finale")

                End If



            ' --------------------------------------------------------------------------

            ' CATALOG ITEM — VIDEO GỌN NHẸ (Mật độ 275 Frames di chuyển)

            ' --------------------------------------------------------------------------

            Else

                shots.Add("Extents_Pullback_Reveal")

                shots.Add("Orbit_Majestic")

                shots.Add("Flowline_Track")

                shots.Add("Crane_Descent")

                shots.Add("Energy_Path_Reveal")

                shots.Add("Precision_Lock")

                shots.Add("Top_Down_God_Eye")

                shots.Add("Material_Kiss")

                shots.Add("Fit_To_View_Finale")

            End If



            Return shots

        End Function
    End Sub
End Class
