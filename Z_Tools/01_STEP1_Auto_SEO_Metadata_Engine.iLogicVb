' ==============================================================================
' 01_STEP1_Auto_SEO_Metadata_Engine.iLogicVb
' BƯỚC 1: Đọc iProperties từ Model & Tự động Đúc 2 File Dashboard HTML (CGTrader & Fab)
' ==============================================================================

AddReference "System.Windows.Forms"
AddReference "System.Private.Windows.Core"

Public Class ThisRule
    Private Declare Auto Function GetAsyncKeyState Lib "user32.dll" (ByVal vKey As Integer) As Short
    Private Const VK_ESCAPE As Integer = &H1B

    Private Function CheckEscape() As Boolean
        Try
            System.Windows.Forms.Application.DoEvents()
            If GetAsyncKeyState(VK_ESCAPE) < 0 Then
                Return True
            End If
        Catch
        End Try
        Return False
    End Function

    Private Sub SafeYield(Optional ByVal sleepMs As Integer = 15)
        Try
            System.Windows.Forms.Application.DoEvents()
            If sleepMs > 0 Then System.Threading.Thread.Sleep(sleepMs)
            GC.Collect()
        Catch
        End Try
    End Sub

    Public Sub Main()
        Try
            If ThisApplication.ActiveDocument Is Nothing Then
                MessageBox.Show("Vui lòng mở 1 mô hình 3D (.iam / .ipt) trước khi chạy Bước 1!", "Thông Báo", MessageBoxButtons.OK, MessageBoxIcon.Warning)
                Exit Sub
            End If
            iLogicVb.Automation.RunExternalRule(ThisApplication.ActiveDocument, "d:\WT3D_Project\Z_Tools\Auto_SEO_Metadata_Engine.iLogicVb")
        Catch ex As Exception
            MessageBox.Show("Lỗi thực thi Bước 1: " & ex.Message, "Báo Động Bước 1")
        End Try
    End Sub
End Class
